module dell-ftos-cli-3.0 {
  yang-version 1.1;
  namespace "http://tail-f.com/ns/ned-id/dell-ftos-cli-3.0";
  prefix dell-ftos-cli-3.0;

  import dell-ftos-cli {
    prefix family;
  }

  identity dell-ftos-cli-3.0 {
    base family:dell-ftos-cli;
  }
}
