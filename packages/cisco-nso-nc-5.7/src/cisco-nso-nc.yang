module cisco-nso-nc {
  yang-version 1.1;
  namespace "http://tail-f.com/ns/ned-id/cisco-nso-nc";
  prefix cisco-nso-nc;

  import tailf-common {
    prefix tailf;
  }

  import tailf-ncs-ned {
    prefix ned;
  }

  identity cisco-nso-nc {
    tailf:abstract;
    base ned:lsa-netconf;
  }
}
