submodule tailf-ncs-common {
  // Generated by yanger -t ncs
  tailf:mount-id "cisco-nso-nc-5.7:cisco-nso-nc-5.7";

  yang-version 1.1;
  belongs-to tailf-ncs {
    prefix ncs;
  }

  import tailf-common {
    prefix tailf;
  }
  import tailf-ncs-internal-mount {
    prefix ncs-internal;
  }

  organization
    "Tail-f Systems";
  description
    "This submodule contains a collection of common YANG definitions
     for NCS.

     Copyright 2012-2019 Cisco Systems, Inc.
     All rights reserved.
     Permission is hereby granted to redistribute this file without
     modification.";

  revision 2019-11-28 {
    description
      "Released as part of NCS-5.3.

       Added typedef trace-output.";
  }
  revision 2014-04-02 {
    description
      "Released as part of NCS-3.1.

       Added typedef outformat-deep-check-sync.";
  }
  revision 2013-11-12 {
    description
      "Released as part of NCS-3.0.

       Added trace-flag typedef.";
  }
  revision 2012-08-30 {
    description
      "Released as part of NCS-2.0.";
  }

  typedef ncs_template_outformat2 {
    type string;
  }

  typedef ncs_template_outformat3 {
    type string;
  }

  typedef ncs_template_outformat4 {
    type string;
  }

  typedef ncs_template_outformat-deep-check-sync {
    type string;
  }

  typedef ncs_template_trace-flag {
    type string;
  }

  typedef ncs_template_trace-output {
    type string;
  }

  typedef ncs_rpc_notif_outformat2 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
    }
  }

  typedef ncs_rpc_notif_outformat3 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
      enum "native" {
        tailf:code-name "outformat_native";
        description
          "The actual data in native format that would be sent to
           the device.";
      }
    }
  }

  typedef ncs_rpc_notif_outformat4 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
      enum "native" {
        tailf:code-name "outformat_native";
        description
          "The actual data in native format that would be sent to
           the device";
      }
      enum "boolean";
    }
  }

  typedef ncs_rpc_notif_outformat-deep-check-sync {
    type enumeration {
      enum "cli" {
        tailf:code-name "deep_cs_cli";
        description
          "The CLI config that would have to be applied
           to the device(s) in order for the service to
           become in sync with the network.";
      }
      enum "xml" {
        tailf:code-name "deep_cs_xml";
        description
          "The XML (NETCONF format) that would have to be
           applied to the device(s) in order for the service to
           become in sync with the network.";
      }
      enum "boolean" {
        tailf:code-name "deep_cs_boolean";
        description
          "Returns if the service is in sync or not.";
      }
    }
  }

  typedef ncs_rpc_notif_trace-flag {
    type enumeration {
      enum "false" {
        tailf:info
          "Trace is disabled";
        description
          "Trace is disabled.";
      }
      enum "raw" {
        tailf:info
          "Raw, unformatted data";
        description
          "The raw, unformatted trace data is logged.  The format
           of the data depends on the type of the managed device.";
      }
      enum "pretty" {
        tailf:info
          "Pretty-printed data";
        description
          "The trace data is pretty-printed to the log files.
           The format of the pretty printed data depends on the type
           of the managed device.";
      }
    }
  }

  typedef ncs_rpc_notif_trace-output {
    type bits {
      bit file {
        tailf:info
          "Write trace to file";
        description
          "Write trace to file.";
        tailf:code-name "to_file";
      }
      bit external {
        tailf:info
          "Write trace to external command";
        description
          "Write trace to external command.";
        tailf:code-name "to_external";
      }
    }
  }

  typedef live_ncs_outformat2 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
    }
  }

  typedef live_ncs_outformat3 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
      enum "native" {
        tailf:code-name "outformat_native";
        description
          "The actual data in native format that would be sent to
           the device.";
      }
    }
  }

  typedef live_ncs_outformat4 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
      enum "native" {
        tailf:code-name "outformat_native";
        description
          "The actual data in native format that would be sent to
           the device";
      }
      enum "boolean";
    }
  }

  typedef live_ncs_outformat-deep-check-sync {
    type enumeration {
      enum "cli" {
        tailf:code-name "deep_cs_cli";
        description
          "The CLI config that would have to be applied
           to the device(s) in order for the service to
           become in sync with the network.";
      }
      enum "xml" {
        tailf:code-name "deep_cs_xml";
        description
          "The XML (NETCONF format) that would have to be
           applied to the device(s) in order for the service to
           become in sync with the network.";
      }
      enum "boolean" {
        tailf:code-name "deep_cs_boolean";
        description
          "Returns if the service is in sync or not.";
      }
    }
  }

  typedef live_ncs_trace-flag {
    type enumeration {
      enum "false" {
        tailf:info
          "Trace is disabled";
        description
          "Trace is disabled.";
      }
      enum "raw" {
        tailf:info
          "Raw, unformatted data";
        description
          "The raw, unformatted trace data is logged.  The format
           of the data depends on the type of the managed device.";
      }
      enum "pretty" {
        tailf:info
          "Pretty-printed data";
        description
          "The trace data is pretty-printed to the log files.
           The format of the pretty printed data depends on the type
           of the managed device.";
      }
    }
  }

  typedef live_ncs_trace-output {
    type bits {
      bit file {
        tailf:info
          "Write trace to file";
        description
          "Write trace to file.";
        tailf:code-name "to_file";
      }
      bit external {
        tailf:info
          "Write trace to external command";
        description
          "Write trace to external command.";
        tailf:code-name "to_external";
      }
    }
  }

  typedef outformat2 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
    }
  }

  typedef outformat3 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
      enum "native" {
        tailf:code-name "outformat_native";
        description
          "The actual data in native format that would be sent to
           the device.";
      }
    }
  }

  typedef outformat4 {
    type enumeration {
      enum "cli" {
        tailf:code-name "outformat_cli";
        description
          "NCS CLI curly bracket format.";
      }
      enum "xml" {
        tailf:code-name "outformat_xml";
        description
          "NETCONF XML edit-config format, i.e., the edit-config that
           would be applied locally (at NCS) to get a config
           that is equal to that of the managed device.";
      }
      enum "native" {
        tailf:code-name "outformat_native";
        description
          "The actual data in native format that would be sent to
           the device";
      }
      enum "boolean";
    }
  }

  typedef outformat-deep-check-sync {
    type enumeration {
      enum "cli" {
        tailf:code-name "deep_cs_cli";
        description
          "The CLI config that would have to be applied
           to the device(s) in order for the service to
           become in sync with the network.";
      }
      enum "xml" {
        tailf:code-name "deep_cs_xml";
        description
          "The XML (NETCONF format) that would have to be
           applied to the device(s) in order for the service to
           become in sync with the network.";
      }
      enum "boolean" {
        tailf:code-name "deep_cs_boolean";
        description
          "Returns if the service is in sync or not.";
      }
    }
  }

  typedef trace-flag {
    type enumeration {
      enum "false" {
        tailf:info
          "Trace is disabled";
        description
          "Trace is disabled.";
      }
      enum "raw" {
        tailf:info
          "Raw, unformatted data";
        description
          "The raw, unformatted trace data is logged.  The format
           of the data depends on the type of the managed device.";
      }
      enum "pretty" {
        tailf:info
          "Pretty-printed data";
        description
          "The trace data is pretty-printed to the log files.
           The format of the pretty printed data depends on the type
           of the managed device.";
      }
    }
  }

  typedef trace-output {
    type bits {
      bit file {
        tailf:info
          "Write trace to file";
        description
          "Write trace to file.";
        tailf:code-name "to_file";
      }
      bit external {
        tailf:info
          "Write trace to external command";
        description
          "Write trace to external command.";
        tailf:code-name "to_external";
      }
    }
  }
}
