submodule tailf-ncs-log {
  // Generated by yanger -t ncs
  tailf:mount-id "cisco-nso-nc-5.7:cisco-nso-nc-5.7";

  yang-version 1.1;
  belongs-to tailf-ncs {
    prefix ncs;
  }

  import ietf-yang-types {
    prefix yang;
  }
  import tailf-common {
    prefix tailf;
  }
  import tailf-ncs-internal-mount {
    prefix ncs-internal;
  }

  organization
    "Tail-f Systems";
  description
    "This module contains a collection of YANG definitions for
     configuring log data in NCS.

     Copyright 2016-2019 Cisco Systems, Inc.
     All rights reserved.
     Permission is hereby granted to redistribute this file without
     modification.";

  revision 2019-04-09 {
    description
      "Released as part of NCS-5.1.

       Removed leaf 'result' from purge action.";
  }
  revision 2016-11-24 {
    description
      "Released as part of NCS-4.3.

       Initial revision.";
  }

  typedef ncs_template_log-entry-level-t {
    type string;
    description
      "Levels used for identifying the severity of an event.
       Levels are organized from least specific to most where
       'all' is least specific and 'error' is most specific.";
  }

  typedef ncs_template_log-entry-t {
    description
      "This leaf identifies the specific log entry.";
    type string;
  }

  typedef ncs_rpc_notif_log-entry-level-t {
    type enumeration {
      enum "all" {
        tailf:code-name "log-entry-level-all";
        value 1;
      }
      enum "trace" {
        tailf:code-name "log-entry-level-trace";
        value 2;
      }
      enum "debug" {
        tailf:code-name "log-entry-level-debug";
        value 3;
      }
      enum "info" {
        tailf:code-name "log-entry-level-info";
        value 4;
      }
      enum "warn" {
        tailf:code-name "log-entry-level-warn";
        value 5;
      }
      enum "error" {
        tailf:code-name "log-entry-level-error";
        value 6;
      }
    }
    description
      "Levels used for identifying the severity of an event.
       Levels are organized from least specific to most where
       'all' is least specific and 'error' is most specific.";
  }

  typedef ncs_rpc_notif_log-entry-t {
    description
      "This leaf identifies the specific log entry.";
    // NCS patched to string, due to LSA partial NED
    type string;
  }

  typedef live_ncs_log-entry-level-t {
    type enumeration {
      enum "all" {
        tailf:code-name "log-entry-level-all";
        value 1;
      }
      enum "trace" {
        tailf:code-name "log-entry-level-trace";
        value 2;
      }
      enum "debug" {
        tailf:code-name "log-entry-level-debug";
        value 3;
      }
      enum "info" {
        tailf:code-name "log-entry-level-info";
        value 4;
      }
      enum "warn" {
        tailf:code-name "log-entry-level-warn";
        value 5;
      }
      enum "error" {
        tailf:code-name "log-entry-level-error";
        value 6;
      }
    }
    description
      "Levels used for identifying the severity of an event.
       Levels are organized from least specific to most where
       'all' is least specific and 'error' is most specific.";
  }

  typedef live_ncs_log-entry-t {
    description
      "This leaf identifies the specific log entry.";
    // NCS patched to string, due to LSA partial NED
    type string;
  }

  typedef log-entry-level-t {
    type enumeration {
      enum "all" {
        tailf:code-name "log-entry-level-all";
        value 1;
      }
      enum "trace" {
        tailf:code-name "log-entry-level-trace";
        value 2;
      }
      enum "debug" {
        tailf:code-name "log-entry-level-debug";
        value 3;
      }
      enum "info" {
        tailf:code-name "log-entry-level-info";
        value 4;
      }
      enum "warn" {
        tailf:code-name "log-entry-level-warn";
        value 5;
      }
      enum "error" {
        tailf:code-name "log-entry-level-error";
        value 6;
      }
    }
    description
      "Levels used for identifying the severity of an event.
       Levels are organized from least specific to most where
       'all' is least specific and 'error' is most specific.";
  }

  typedef log-entry-t {
    description
      "This leaf identifies the specific log entry.";
    // NCS patched to string, due to LSA partial NED
    type string;
  }

  grouping ncs_template_log-data {
    description
      "NCS or user specific code may choose to populate a log entry
       to indicate important events associated with it.";
    // NCS drop config false container log
  }

  grouping ncs_template_filter-input {
    leaf type {
      type ncs_template_log-entry-t;
    }
    leaf level {
      type ncs_template_log-entry-level-t;
    }
    container older-than {
      presence "Age specification";
      description
        "Matches the 'when' leaf in the log entry.";
      choice age-spec {
        case seconds {
          leaf seconds {
            type string;
          }
        }
        case minutes {
          leaf minutes {
            type string;
          }
        }
        case hours {
          leaf hours {
            type string;
          }
        }
        case days {
          leaf days {
            type string;
          }
        }
        case weeks {
          leaf weeks {
            type string;
          }
        }
      }
    }
  }

  grouping ncs_rpc_notif_log-data {
    description
      "NCS or user specific code may choose to populate a log entry
       to indicate important events associated with it.";
    container log {
      config false;
      // NCS drop tailf:cdb-oper
      // NCS drop tailf:action
      list log-entry {
        key "when";
        leaf when {
          type yang:date-and-time;
        }
        leaf type {
          description
            "What type of log entry is this.";
          type ncs_rpc_notif_log-entry-t;
          mandatory true;
        }
        leaf level {
          description
            "What level this log entry has.";
          type ncs_rpc_notif_log-entry-level-t;
          mandatory true;
        }
        leaf message {
          type string;
        }
      }
    }
  }

  grouping ncs_rpc_notif_filter-input {
    leaf type {
      type ncs_rpc_notif_log-entry-t;
    }
    leaf level {
      type ncs_rpc_notif_log-entry-level-t;
    }
    container older-than {
      presence "Age specification";
      description
        "Matches the 'when' leaf in the log entry.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  grouping live_ncs_log-data {
    description
      "NCS or user specific code may choose to populate a log entry
       to indicate important events associated with it.";
    container log {
      // NCS drop tailf:cdb-oper
      tailf:action purge {
        tailf:actionpoint ncsproxy {
          tailf:internal;
        }
        tailf:info
          "Remove log entries";
        // NCS drop tailf:actionpoint
        description
          "This action requests to delete log entries from the log-entry
           list according to the supplied criteria.";
        input {
          uses live_ncs_filter-input;
        }
        output {
          leaf purged-log-entries {
            type uint16;
          }
        }
      }
      list log-entry {
        key "when";
        leaf when {
          type yang:date-and-time;
        }
        leaf type {
          description
            "What type of log entry is this.";
          type live_ncs_log-entry-t;
          // NCS drop mandatory statement
        }
        leaf level {
          description
            "What level this log entry has.";
          type live_ncs_log-entry-level-t;
          // NCS drop mandatory statement
        }
        leaf message {
          type string;
        }
      }
    }
  }

  grouping live_ncs_filter-input {
    leaf type {
      type live_ncs_log-entry-t;
    }
    leaf level {
      type live_ncs_log-entry-level-t;
    }
    container older-than {
      presence "Age specification";
      description
        "Matches the 'when' leaf in the log entry.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  grouping log-data {
    description
      "NCS or user specific code may choose to populate a log entry
       to indicate important events associated with it.";
    // NCS drop config false container log
  }

  grouping filter-input {
    leaf type {
      type log-entry-t;
    }
    leaf level {
      type log-entry-level-t;
    }
    container older-than {
      presence "Age specification";
      description
        "Matches the 'when' leaf in the log entry.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  identity device-modified {
    description
      "When a device is modified and has a service backpointer,
       we log with this log entry type";
    base log-entry;
  }

  identity service-modified {
    description
      "When a service is modified, we log with this log entry type";
    base log-entry;
  }

  identity log-entry {
    description
      "This is a base type from which all log entries can be derived.

       All code that adds log-entries must always provide their own
       identity, derived from this one.";
  }
}
