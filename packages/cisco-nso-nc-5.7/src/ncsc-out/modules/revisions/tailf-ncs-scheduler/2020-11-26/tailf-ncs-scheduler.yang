module tailf-ncs-scheduler {
  // Generated by yanger -t ncs
  tailf:mount-id "cisco-nso-nc-5.7:cisco-nso-nc-5.7";
  tailf:ncs-device-type "netconf";

  namespace "http://tail-f.com/ns/ncs-scheduler";
  prefix scheduler;

  import ietf-yang-types {
    prefix yang;
  }
  import tailf-common {
    prefix tailf;
  }
  import tailf-ncs-internal-mount {
    prefix ncs;
  }

  organization
    "Tail-f Systems";
  description
    "This module contains a collection of YANG definitions for
     configuring scheduled tasks in NCS.

     Copyright 2017-2020 Cisco Systems, Inc.
     All rights reserved.
     Permission is hereby granted to redistribute this file without
     modification.";

  revision 2020-11-26 {
    description
      "Released as part of NCS-5.5.

       Made /scheduler/task/local-user leaf into an internal callpoint.";
  }
  revision 2020-06-25 {
    description
      "Released as part of NCS-5.4.

       Non-backwards-compatible changes have been introduced.

       Moved /scheduler/task/history to /scheduler/task/history/history-entry
       and made it persistent. The YANG node /scheduler/task/history is
       now a container.

       Added /scheduler/task/history/history-entry/action-node leaf.

       Added /scheduler/task/history/history-entry/ha-node-id leaf.

       Added /scheduler/task/history/max-size leaf.

       Added /scheduler/task/history/purge action.

       Made /scheduler/suspended leaf into an internal callpoint.

       Renamed /scheduler/task/is-running leaf to running
       and made it into an internal callpoint.

       Removed must expression from /scheduler/task/time leaf.

       The type of next-run-time leaf in /scheduler/task/get-next-run-times
       action changed from string to yang:date-and-time.";
  }
  revision 2019-10-17 {
    description
      "Released as part of NCS-5.2.1.

       Added sequence-no leaf as part of key to
       /scheduler/task/history.";
  }
  revision 2019-05-16 {
    description
      "Released as part of NCS-5.1.1.

       Updated the description for /scheduler/task/time.";
  }
  revision 2018-06-21 {
    description
      "Released as part of NCS-4.7.

       Added /scheduler/task/enabled.

       The type of /scheduler/task/action-name changed from
       yang:yang-identifier to tailf:identifier-ref.

       Added /scheduler/task/history/result.";
  }
  revision 2017-11-30 {
    description
      "Released as part of NCS-4.5.2.

       Added /scheduler/task/ha-mode.
       Added /scheduler/task/ha-node-id.

       Added /scheduler/task/time.
       Added /scheduler/task/keep.

       The type of /scheduler/task/history/duration changed from
       string to decimal64.";
  }
  revision 2017-09-28 {
    description
      "Released as part of NCS-4.5.

       Initial revision.";
  }

  grouping ncs_template_filter-input {
    leaf succeeded {
      type string;
    }
    container older-than {
      presence "Age specification";
      description
        "Matches the 'when' leaf in the history entry.";
      choice age-spec {
        case seconds {
          leaf seconds {
            type string;
          }
        }
        case minutes {
          leaf minutes {
            type string;
          }
        }
        case hours {
          leaf hours {
            type string;
          }
        }
        case days {
          leaf days {
            type string;
          }
        }
        case weeks {
          leaf weeks {
            type string;
          }
        }
      }
    }
  }

  grouping ncs_rpc_notif_filter-input {
    leaf succeeded {
      type boolean;
    }
    container older-than {
      presence "Age specification";
      description
        "Matches the 'when' leaf in the history entry.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  grouping live_ncs_filter-input {
    leaf succeeded {
      type boolean;
    }
    container older-than {
      presence "Age specification";
      description
        "Matches the 'when' leaf in the history entry.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  grouping filter-input {
    leaf succeeded {
      type boolean;
    }
    container older-than {
      presence "Age specification";
      description
        "Matches the 'when' leaf in the history entry.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  augment "/ncs:devices/ncs:device/ncs:config" {
    container scheduler {
      tailf:ncs-device-type "netconf";
      tailf:display-when "not(../../ncs:module) or ../../ncs:module[ncs:name='tailf-ncs-scheduler']";
      description
        "Time-based job scheduler suitable for scheduling periodic
         background work.";
      tailf:action suspend {
        tailf:actionpoint ncsproxy {
          tailf:internal;
        }
        tailf:display-when "../suspended = 'false'" {
          tailf:xpath-root 3;
        }
        description
          "Suspend all tasks in the scheduler.";
        // NCS drop tailf:actionpoint
      }
      tailf:action resume {
        tailf:actionpoint ncsproxy {
          tailf:internal;
        }
        tailf:display-when "../suspended = 'true'" {
          tailf:xpath-root 3;
        }
        description
          "Resume all tasks in the scheduler.";
        // NCS drop tailf:actionpoint
      }
      // NCS drop config false leaf suspended
      list task {
        tailf:info
          "The list of configured tasks.";
        description
          "Examples:

             Run sync-from on all devices 2 AM on the 1st every month:

               name: sync
               schedule: 0 2 1 * *
               action-name: sync-from
               action-node: /devices

             Purge the completed queue-item list 4:30 AM every Sunday:

               name: purge
               schedule: 30 4 * * 0
               action-name: purge
               action-node: /devices/commit-queue/completed";
        key "name";
        leaf name {
          type string;
          description
            "A unique name for this task.";
        }
        // NCS drop tailf:callpoint
        choice trigger {
          mandatory true;
          case schedule {
            leaf schedule {
              description
                "Standard Vixie Cron expression to represent the
                 periodicity in which the task should run.

                 ---------- minute (0 - 59)
                 | ---------- hour (0 - 23)
                 | | ---------- day of month (1 - 31)
                 | | | ---------- month (1 - 12)
                 | | | | ---------- day of week (0 - 6) (Sunday to Saturday)
                 | | | | |
                 * * * * *";
              type string;
              // NCS drop tailf:validate
            }
          }
          case time {
            leaf time {
              description
                "A particular time when the task should run.

                 The task will be triggered at the second.
                 Fractions of the second will be ignored.

                 The time zone offset -00:00 indicates an unknown time zone
                 which the scheduler interprets as local time.";
              type yang:date-and-time;
              mandatory true;
            }
            leaf keep {
              description
                "Keep configured task after it has finished successfully.";
              type empty;
            }
          }
        }
        leaf action-node {
          description
            "When the task is triggered, the 'action-name' action is invoked
             on the 'action-node' instance. The action is run as the user
             that configured the task.

             If the 'action-node' is given as an XPath 1.0 expression, the
             expression is evaluated with the root as the context node,
             and the expression must return a node set. The 'action-name'
             action is invoked on the nodes in this node set.";
          type union {
            // NCS patched to string, due to LSA partial NED
            type string;
            type yang:xpath1.0;
          }
          mandatory true;
          // NCS drop tailf:validate
        }
        leaf action-name {
          description
            "The action to be invoked. Can be given either as just the name
             of the action without a prefix, or the name of the action
             prefixed with the prefix defined in the YANG module where the
             action is defined. The prefix is required if more than one
             action with the given name is present due to augmentations.";
          type tailf:identifier-ref;
          mandatory true;
        }
        leaf action-params {
          description
            "Action parameters in XML format.";
          type string;
        }
        leaf ha-mode {
          description
            "The HA mode in which the task will run.

             The setting will not have any effect if HA isn't configured.";
          type enumeration {
            enum "master";
            enum "slave";
          }
          default "master";
        }
        leaf ha-node-id {
          when "../ha-mode = 'slave'" {
            tailf:xpath-root 3;
          }
          type string;
          description
            "The HA cluster node on which the task is allowed to run.";
        }
        leaf enabled {
          description
            "Whether the task is enabled or not.";
          type boolean;
          default "true";
        }
        // NCS drop fully hidden leaf 'local-user'
        // NCS drop config false leaf running
        container history {
          description
            "History of last runs.";
          leaf max-size {
            type union {
              type enumeration {
                enum "unlimited";
              }
              type uint32 {
                range "0 .. max";
              }
            }
            default "10";
            description
              "Max size of ../history-entry list. When the maximum size
               is reached, the oldest list entry is purged.";
          }
          tailf:action purge {
            tailf:actionpoint ncsproxy {
              tailf:internal;
            }
            tailf:info
              "Remove history entries";
            // NCS drop tailf:actionpoint
            description
              "This action requests to delete history entries from the
               history-entry list according to the supplied criteria.";
            input {
              uses filter-input;
            }
            output {
              leaf purged-history-entries {
                type uint32;
              }
            }
          }
          // NCS drop config false list 'history-entry'
        }
        tailf:action get-next-run-times {
          tailf:actionpoint ncsproxy {
            tailf:internal;
          }
          description
            "Display the next run times for the task.";
          // NCS drop tailf:actionpoint
          input {
            leaf display {
              type uint16 {
                range "1..100";
              }
              default "5";
            }
          }
          output {
            leaf-list next-run-time {
              type yang:date-and-time;
            }
          }
        }
      }
    }
  }
  augment "/ncs:devices/ncs:device/ncs:live-status" {
    container scheduler {
      tailf:ncs-device-type "netconf";
      tailf:display-when "not(../../ncs:module) or ../../ncs:module[ncs:name='tailf-ncs-scheduler'] or (../../ncs:live-status-protocol[not(ncs:capability)]) or (../../ncs:live-status-protocol/ncs:capability/ncs:module[.='tailf-ncs-scheduler'])";
      description
        "Time-based job scheduler suitable for scheduling periodic
         background work.";
      tailf:action suspend {
        tailf:actionpoint ncsproxy {
          tailf:internal;
        }
        tailf:display-when "../suspended = 'false'" {
          tailf:xpath-root 3;
        }
        description
          "Suspend all tasks in the scheduler.";
        // NCS drop tailf:actionpoint
      }
      tailf:action resume {
        tailf:actionpoint ncsproxy {
          tailf:internal;
        }
        tailf:display-when "../suspended = 'true'" {
          tailf:xpath-root 3;
        }
        description
          "Resume all tasks in the scheduler.";
        // NCS drop tailf:actionpoint
      }
      leaf suspended {
        description
          "Whether the scheduler is suspended or not.";
        type boolean;
        // NCS drop default statement
        // NCS drop tailf:callpoint
      }
      list task {
        tailf:info
          "The list of configured tasks.";
        description
          "Examples:

             Run sync-from on all devices 2 AM on the 1st every month:

               name: sync
               schedule: 0 2 1 * *
               action-name: sync-from
               action-node: /devices

             Purge the completed queue-item list 4:30 AM every Sunday:

               name: purge
               schedule: 30 4 * * 0
               action-name: purge
               action-node: /devices/commit-queue/completed";
        key "name";
        leaf name {
          type string;
          description
            "A unique name for this task.";
        }
        // NCS drop tailf:callpoint
        choice trigger {
          // NCS drop mandatory statement
          case schedule {
            leaf schedule {
              description
                "Standard Vixie Cron expression to represent the
                 periodicity in which the task should run.

                 ---------- minute (0 - 59)
                 | ---------- hour (0 - 23)
                 | | ---------- day of month (1 - 31)
                 | | | ---------- month (1 - 12)
                 | | | | ---------- day of week (0 - 6) (Sunday to Saturday)
                 | | | | |
                 * * * * *";
              type string;
              // NCS drop tailf:validate
            }
          }
          case time {
            leaf time {
              description
                "A particular time when the task should run.

                 The task will be triggered at the second.
                 Fractions of the second will be ignored.

                 The time zone offset -00:00 indicates an unknown time zone
                 which the scheduler interprets as local time.";
              type yang:date-and-time;
              // NCS drop mandatory statement
            }
            leaf keep {
              description
                "Keep configured task after it has finished successfully.";
              type empty;
            }
          }
        }
        leaf action-node {
          description
            "When the task is triggered, the 'action-name' action is invoked
             on the 'action-node' instance. The action is run as the user
             that configured the task.

             If the 'action-node' is given as an XPath 1.0 expression, the
             expression is evaluated with the root as the context node,
             and the expression must return a node set. The 'action-name'
             action is invoked on the nodes in this node set.";
          type union {
            // NCS patched to string, due to LSA partial NED
            type string;
            type yang:xpath1.0;
          }
          // NCS drop mandatory statement
          // NCS drop tailf:validate
        }
        leaf action-name {
          description
            "The action to be invoked. Can be given either as just the name
             of the action without a prefix, or the name of the action
             prefixed with the prefix defined in the YANG module where the
             action is defined. The prefix is required if more than one
             action with the given name is present due to augmentations.";
          type tailf:identifier-ref;
          // NCS drop mandatory statement
        }
        leaf action-params {
          description
            "Action parameters in XML format.";
          type string;
        }
        leaf ha-mode {
          description
            "The HA mode in which the task will run.

             The setting will not have any effect if HA isn't configured.";
          type enumeration {
            enum "master";
            enum "slave";
          }
          // NCS drop default statement
        }
        leaf ha-node-id {
          // NCS drop when statement
          type string;
          description
            "The HA cluster node on which the task is allowed to run.";
        }
        leaf enabled {
          description
            "Whether the task is enabled or not.";
          type boolean;
          // NCS drop default statement
        }
        // NCS drop fully hidden leaf 'local-user'
        leaf running {
          description
            "Whether the task is currently executing.";
          type boolean;
          // NCS drop default statement
          // NCS drop tailf:callpoint
        }
        container history {
          description
            "History of last runs.";
          leaf max-size {
            type union {
              type enumeration {
                enum "unlimited";
              }
              type uint32 {
                range "0 .. max";
              }
            }
            // NCS drop default statement
            description
              "Max size of ../history-entry list. When the maximum size
               is reached, the oldest list entry is purged.";
          }
          tailf:action purge {
            tailf:actionpoint ncsproxy {
              tailf:internal;
            }
            tailf:info
              "Remove history entries";
            // NCS drop tailf:actionpoint
            description
              "This action requests to delete history entries from the
               history-entry list according to the supplied criteria.";
            input {
              uses live_ncs_filter-input;
            }
            output {
              leaf purged-history-entries {
                type uint32;
              }
            }
          }
          list history-entry {
            key "when sequence-no";
            // NCS drop tailf:cdb-oper
            leaf when {
              type yang:date-and-time;
              description
                "When the action was started.";
            }
            leaf sequence-no {
              type uint8;
            }
            leaf duration {
              type decimal64 {
                fraction-digits 3;
              }
              units "seconds";
              description
                "Duration of the action in seconds.";
            }
            leaf succeeded {
              type boolean;
              description
                "Whether the action succeeded or failed.";
            }
            leaf action-node {
              type yang:xpath1.0;
              description
                "The node on which the action was run.";
            }
            leaf ha-node-id {
              type string;
              description
                "The HA cluster node on which the action was run
                 (if run on a slave).";
            }
            anyxml result {
              description
                "Action output in XML format.";
            }
            leaf info {
              type string;
              description
                "Error message in case the action was not successful.";
            }
          }
        }
        tailf:action get-next-run-times {
          tailf:actionpoint ncsproxy {
            tailf:internal;
          }
          description
            "Display the next run times for the task.";
          // NCS drop tailf:actionpoint
          input {
            leaf display {
              type uint16 {
                range "1..100";
              }
              default "5";
            }
          }
          output {
            leaf-list next-run-time {
              type yang:date-and-time;
            }
          }
        }
      }
    }
  }
  augment "/ncs:devices/ncs:template/ncs:ned-id/ncs:config" {
    container scheduler {
      description
        "Time-based job scheduler suitable for scheduling periodic
         background work.";
      // NCS drop config false leaf suspended
      list task {
        // NCS patched for predictable order
        ordered-by user;
        description
          "Examples:

             Run sync-from on all devices 2 AM on the 1st every month:

               name: sync
               schedule: 0 2 1 * *
               action-name: sync-from
               action-node: /devices

             Purge the completed queue-item list 4:30 AM every Sunday:

               name: purge
               schedule: 30 4 * * 0
               action-name: purge
               action-node: /devices/commit-queue/completed";
        key "name";
        leaf name {
          type string;
          description
            "A unique name for this task.";
        }
        choice trigger {
          // NCS drop mandatory statement
          case schedule {
            leaf schedule {
              description
                "Standard Vixie Cron expression to represent the
                 periodicity in which the task should run.

                 ---------- minute (0 - 59)
                 | ---------- hour (0 - 23)
                 | | ---------- day of month (1 - 31)
                 | | | ---------- month (1 - 12)
                 | | | | ---------- day of week (0 - 6) (Sunday to Saturday)
                 | | | | |
                 * * * * *";
              type string;
            }
          }
          case time {
            leaf time {
              description
                "A particular time when the task should run.

                 The task will be triggered at the second.
                 Fractions of the second will be ignored.

                 The time zone offset -00:00 indicates an unknown time zone
                 which the scheduler interprets as local time.";
              type string;
              // NCS drop mandatory statement
            }
            leaf keep {
              description
                "Keep configured task after it has finished successfully.";
              type empty;
            }
          }
        }
        leaf action-node {
          description
            "When the task is triggered, the 'action-name' action is invoked
             on the 'action-node' instance. The action is run as the user
             that configured the task.

             If the 'action-node' is given as an XPath 1.0 expression, the
             expression is evaluated with the root as the context node,
             and the expression must return a node set. The 'action-name'
             action is invoked on the nodes in this node set.";
          type string;
          // NCS drop mandatory statement
        }
        leaf action-name {
          description
            "The action to be invoked. Can be given either as just the name
             of the action without a prefix, or the name of the action
             prefixed with the prefix defined in the YANG module where the
             action is defined. The prefix is required if more than one
             action with the given name is present due to augmentations.";
          type string;
          // NCS drop mandatory statement
        }
        leaf action-params {
          description
            "Action parameters in XML format.";
          type string;
        }
        leaf ha-mode {
          description
            "The HA mode in which the task will run.

             The setting will not have any effect if HA isn't configured.";
          type string;
          // NCS drop default statement
        }
        leaf ha-node-id {
          // NCS drop when statement
          type string;
          description
            "The HA cluster node on which the task is allowed to run.";
        }
        leaf enabled {
          description
            "Whether the task is enabled or not.";
          type string;
          // NCS drop default statement
        }
        // NCS drop fully hidden leaf 'local-user'
        // NCS drop config false leaf running
        container history {
          description
            "History of last runs.";
          leaf max-size {
            type string;
            // NCS drop default statement
            description
              "Max size of ../history-entry list. When the maximum size
               is reached, the oldest list entry is purged.";
          }
          // NCS drop config false list 'history-entry'
        }
      }
    }
  }
}
