module tailf-ncs-netconf-ned-builder {
  // Generated by yanger -t ncs
  tailf:mount-id "cisco-nso-nc-5.7:cisco-nso-nc-5.7";
  tailf:ncs-device-type "netconf";

  yang-version 1.1;
  namespace "http://tail-f.com/ns/ncs/netconf-ned-builder";
  prefix tnnb;

  import tailf-ncs {
    prefix ncs;
  }
  import ietf-yang-types {
    prefix yang;
  }
  import ietf-inet-types {
    prefix inet;
  }
  import ietf-yang-library {
    prefix yanglib;
  }
  import tailf-common {
    prefix tailf;
  }
  import tailf-ncs-internal-mount {
    prefix ncs-internal;
  }

  organization
    "Tail-f Systems";
  description
    "This module defines the Cisco NSO NETCONF NED builder data model.

     Copyright 2019 Cisco Systems, Inc.
     All rights reserved.
     Permission is hereby granted to redistribute this file without
     modification.";

  revision 2020-06-25 {
    description
      "Released as part of NCS-5.4.

       Restricted the type of major-version key leaf of
       /netconf-ned-builder/project list to the type ncs:package-version
       required by tailf-ncs-packages data model.";
  }
  revision 2019-06-27 {
    description
      "Released as part of NCS-5.2.";
  }

  typedef ncs_template_module-status-t {
    type string;
  }

  typedef ncs_template_submodule-status-t {
    type ncs_template_module-status-t;
  }

  typedef ncs_template_build-status-t {
    type string;
  }

  typedef ncs_template_dir-path-t {
    description
      "Path to a directory in the filesystem.";
    type string;
  }

  typedef ncs_rpc_notif_module-status-t {
    type bits {
      bit deselected {
        tailf:code-name "bit_deselected";
      }
      bit selected {
        tailf:code-name "bit_selected";
      }
      bit no-dependencies {
        tailf:code-name "bit_no_deps";
      }
      bit pending {
        tailf:code-name "bit_pending";
      }
      bit downloaded {
        tailf:code-name "bit_downloaded";
      }
      bit download-error {
        tailf:code-name "bit_dl_error";
      }
    }
  }

  typedef ncs_rpc_notif_submodule-status-t {
    type ncs_rpc_notif_module-status-t;
  }

  typedef ncs_rpc_notif_build-status-t {
    type enumeration {
      enum "success";
      enum "error";
    }
  }

  typedef ncs_rpc_notif_dir-path-t {
    description
      "Path to a directory in the filesystem.";
    type string;
  }

  typedef live_ncs_module-status-t {
    type bits {
      bit deselected {
        tailf:code-name "bit_deselected";
      }
      bit selected {
        tailf:code-name "bit_selected";
      }
      bit no-dependencies {
        tailf:code-name "bit_no_deps";
      }
      bit pending {
        tailf:code-name "bit_pending";
      }
      bit downloaded {
        tailf:code-name "bit_downloaded";
      }
      bit download-error {
        tailf:code-name "bit_dl_error";
      }
    }
  }

  typedef live_ncs_submodule-status-t {
    type live_ncs_module-status-t;
  }

  typedef live_ncs_build-status-t {
    type enumeration {
      enum "success";
      enum "error";
    }
  }

  typedef live_ncs_dir-path-t {
    description
      "Path to a directory in the filesystem.";
    type string;
  }

  typedef module-status-t {
    type bits {
      bit deselected {
        tailf:code-name "bit_deselected";
      }
      bit selected {
        tailf:code-name "bit_selected";
      }
      bit no-dependencies {
        tailf:code-name "bit_no_deps";
      }
      bit pending {
        tailf:code-name "bit_pending";
      }
      bit downloaded {
        tailf:code-name "bit_downloaded";
      }
      bit download-error {
        tailf:code-name "bit_dl_error";
      }
    }
  }

  typedef submodule-status-t {
    type module-status-t {
      bit pending;
      bit downloaded;
      bit download-error;
    }
  }

  typedef build-status-t {
    type enumeration {
      enum "success";
      enum "error";
    }
  }

  typedef dir-path-t {
    description
      "Path to a directory in the filesystem.";
    type string;
  }

  augment "/ncs-internal:devices/ncs-internal:device/ncs-internal:config" {
    container netconf-ned-builder {
      tailf:ncs-device-type "netconf";
      tailf:display-when "not(../../ncs-internal:module) or ../../ncs-internal:module[ncs-internal:name='tailf-ncs-netconf-ned-builder']";
      tailf:hidden "tailf-devtools";
      description
        "Top container for the NETCONF NED builder data model. The container is
         invisible in the CLI, unless 'devtools' session parameter is set
         to 'true'.";

      grouping common-leafs {
        description
          "Common parameters for YANG modules and submodules.";
        leaf name {
          type yang:yang-identifier;
          description
            "The YANG module or submodule name.";
        }
        leaf revision {
          type union {
            type yanglib:revision-identifier;
            type string {
              length "0";
            }
          }
          description
            "The YANG module or submodule revision date.
             A zero-length string is used if no revision statement
             is present in the YANG module or submodule.";
        }
      }
      list project {
        key "family-name major-version";
        description
          "An instance of NED project. One project is associated with one device
           which is used as a reference device for the kind of devices the NED
           needs to be built. The key of the project is family-name and
           major-version that are used in the NED name.";
        leaf family-name {
          type string;
          description
            "NED family name";
        }
        leaf major-version {
          type ncs:package-version;
          description
            "NED major version";
        }
        leaf device {
          mandatory true;
          description
            "Reference device for the kind of devices the NED is built for.";
          type leafref {
            path "/ncs-internal:devices/ncs-internal:device/ncs-internal:config/ncs:devices/ncs:device/ncs:name" {
              tailf:xpath-root 3;
            }
          }
        }
        leaf local-user {
          mandatory true;
          type string;
          description
            "The NETCONF NED builder will authenticate to device with the
             credentials configured for this NSO user. It is adviced to not
             configure the 'same-pass' option for this user to communicate
             with the device, otherwise the NETCONF NED builder will not be
             able to communicate with the device when the configured user is
             not logged into NSO.";
        }
        leaf vendor {
          mandatory true;
          type string;
          description
            "Vendor field is a mandatory meta-data for the NED package, stored
             in the package-meta-data.xml.";
        }
        leaf max-download-threads {
          default "3";
          type uint8;
          description
            "The NETCONF NED builder will download YANG models in multiple
             threads, and multiple NETCONF session will be open simultaneously
             towards the device corresponding to the number of threads. This
             value indicates the maximum number of download threads launched by
             this NETCONF NED builder project.";
        }
        // NCS drop config false leaf 'download-cache-path'
        // NCS drop config false leaf 'ned-directory-path'
        // NCS drop config false leaf 'build-status'
        // NCS drop config false leaf 'build-error-info'
        // NCS drop config false leaf 'compiler-output'
        action fetch-module-list {
          tailf:actionpoint ncsproxy {
            tailf:internal;
          }
          description
            "This action initiates connection to the device and collects
             information about the supported data models from capabilities and
             ietf-yang-library data model, as well as schemas available through
             ietf-netconf-monitoring data model. The result of this action is
             stored in the 'module' list.";
          // NCS drop tailf:actionpoint
          input {
            must "deref(../../device)/device-type/ned-id = 'ned:netconf'" {
              tailf:xpath-root 3;
              tailf:dependency "../../device";
            }
            leaf overwrite {
              type empty;
              description
                "This leaf indiates that the list of modules should be re-fetched,
                 leading to the current selection status being reset and current
                 download cache being cleared.";
            }
          }
        }
        action build-ned {
          tailf:actionpoint ncsproxy {
            tailf:internal;
          }
          description
            "This action creates a minimal NED structure and runs the compiler
             to build the models for NSO. This NED does not have a netsim
             directory nor Makefile. It is adviced to avoid modifying such NED
             by manual intervention, but only by modifying the module selection in
             NSO and running this action again.

             In case of success the compiled NED is stored in NSO state and may
             be exported with the 'export-ned' action. In case of failure the NSO
             only keeps the compiler output in CDB (see 'build-warning' and
             'build-error' leafs on modules and submodules and 'compiler-output'
             hidden leaf), but the actual copy of the failed NED is deleted.

             In cases the NED might require more advanced intervention such as
             modification of YANG files or making a netsim device, it is adviced
             to make a development NED using 'make-development-ned' action.";
          // NCS drop tailf:actionpoint
          input {
            leaf overwrite {
              type empty;
              description
                "By default we will not overwrite an existing NED. This option
                 tells NSO to delete the existing copy of the NED and try again.";
            }
          }
        }
        action make-development-ned {
          tailf:actionpoint ncsproxy {
            tailf:internal;
          }
          description
            "This action creates a development NED package in the specified
             parent directory, but does not build it. The package needs to be
             built separately by running 'make' in its src/ subdirectory. The
             development NED package supports netsim and the user has the freedom
             of making modifications to the YANG files or build process.";
          // NCS drop tailf:actionpoint
          input {
            leaf in-directory {
              mandatory true;
              type dir-path-t;
              tailf:cli-completion-actionpoint dir-path-comp;
              description
                "The NED directory will be created as subdirectory to the
                 specified one. The user must have write access to the specified
                 directory.";
            }
            leaf overwrite {
              type empty;
              description
                "If the file with the generated name already exists in the
                 specified directory, then replace it with the new one.

                 If the file exists in the directory and this option is not
                 specified, then the action will fail.";
            }
          }
          output {
            leaf ned-path {
              mandatory true;
              type string;
              description
                "Absolute path to the generated NED directory.";
            }
          }
        }
        action export-ned {
          tailf:actionpoint ncsproxy {
            tailf:internal;
          }
          description
            "This action will export the NED previously built with 'build-ned'
             action in form of tarball. The action takes as input the target
             directory to write the tar-file into, and the actual file name is
             generated internally according to the naming convention
             'ncs-<version>-<ned family>-<ned version>.tar.gz'.";
          // NCS drop tailf:actionpoint
          input {
            leaf to-directory {
              mandatory true;
              type dir-path-t;
              tailf:cli-completion-actionpoint dir-path-comp;
              description
                "The tar file containing the NED will be created in the specified
                 directory. The user must have write access to the specified
                 directory.";
            }
            leaf overwrite {
              type empty;
              description
                "If the file with the generated name already exists in the
                 specified directory, then replace it with the new one.

                 If the file exists in the directory and this option is not
                 specified, then the action will fail.";
            }
          }
          output {
            leaf tar-file {
              mandatory true;
              type string;
              description
                "Absolute path to the generated tar file.";
            }
          }
        }
        action save-selection {
          tailf:actionpoint ncsproxy {
            tailf:internal;
          }
          description
            "Saves current selection with specified name under
             /netconf-ned-builder/profile list. The selection may be
             modified, exported into XML file and loaded on another system
             or reused to make similar NED.";
          // NCS drop tailf:actionpoint
          input {
            leaf profile {
              mandatory true;
              must 'not(/netconf-ned-builder/profile[name=current()])' {
                tailf:xpath-root 3;
              }
              type string;
              description
                "Name of the profile to save. The profile must not exist.";
            }
            leaf no-revisions {
              type empty;
              description
                "Save only module names as a profile, without revision data.";
            }
          }
        }

        grouping import-list {
          list import {
            key "name";
            uses common-leafs;
            description
              "List of import dependencies for this module or submodule
               containing imported module and possibly revision if this
               information is available.";
          }
        }

        grouping location-leaf-list {
          leaf-list location {
            type union {
              type enumeration {
                enum "NETCONF";
              }
              type inet:uri;
            }
            description
              "One or more locations from which the module or submodule can be
               retrieved.

               The special value 'NETCONF' means that the module or submodule is
               obtainable using NETCONF get-schema RPC.";
          }
        }

        grouping additional-info {
          leaf select-info {
            type string;
            description
              "This leaf provides additional information in case of errors
               selecting or downloading module.";
          }
          leaf build-warning {
            type string;
            tailf:cli-preformatted;
            description
              "This leaf contains compiler warnings related to this module,
               as printed by the compiler when building the NED.";
          }
          leaf build-error {
            type string;
            tailf:cli-preformatted;
            description
              "This leaf contains compiler errors related to this module,
               as printed by the compiler when building the NED.";
          }
        }
        // NCS drop config false list module
      }
      list profile {
        key "name";
        description
          "This list contains profiles, which are reusable selections of
           modules. The module name is mandatory, while the revision is
           optional which makes it possible to reuse between different device
           versions, e.g. to generate a new version of the NED for
           the upgraded device.";
        leaf name {
          type string;
          description
            "The name of the profile.";
        }
        list module {
          key "name";
          // NCS expand uses statement
          leaf name {
            type yang:yang-identifier;
            description
              "The YANG module or submodule name.";
          }
          leaf revision {
            type union {
              type yanglib:revision-identifier;
              type string {
                length "0";
              }
            }
            description
              "The revision is optional in the profile. If unset, then
               applying the profile will select the module with the
               matching name and any revision.";
          }
        }
        action apply {
          tailf:actionpoint ncsproxy {
            tailf:internal;
          }
          description
            "Select the set of modules defined by this profile in the project
             indicated by the input parameters.";
          // NCS drop tailf:actionpoint
          input {
            leaf family-name {
              mandatory true;
              type leafref {
                path "/ncs-internal:devices/ncs-internal:device/ncs-internal:config/netconf-ned-builder/project/family-name" {
                  tailf:xpath-root 3;
                }
              }
              description
                "Reference to the target project's family-name.";
            }
            leaf major-version {
              mandatory true;
              type leafref {
                path "/ncs-internal:devices/ncs-internal:device/ncs-internal:config/netconf-ned-builder/project[family-name=current()/../family-name]/major-version" {
                  tailf:xpath-root 3;
                }
              }
              description
                "Reference to the target project's major-version.";
            }
            leaf best-effort {
              type empty;
              description
                "Skip modules that do not exist in the project.";
            }
            leaf with-dependencies {
              type empty;
              description
                "By default the list of modules configured in a profile is
                 assumed to be exhaustive so the dependencies for the selected
                 modules are not selected. This option allows to select modules
                 specified by the profile and automatically select their
                 dependencies.";
            }
          }
          output {
            leaf result {
              type enumeration {
                enum "applied";
                enum "not-applied";
              }
              description
                "The result of the profile application.";
            }
            leaf-list selected {
              type string;
              description
                "The list of names of the successfully selected modules.";
            }
            leaf-list not-found {
              type string;
              description
                "The list of names of the modules that were not found in the
                 target project.";
            }
            leaf-list ambiguous {
              type string;
              description
                "The list of names of the modules that were found in more than
                 one instance in the target project.";
            }
          }
        }
      }
    }
  }
  augment "/ncs-internal:devices/ncs-internal:device/ncs-internal:live-status" {
    container netconf-ned-builder {
      tailf:ncs-device-type "netconf";
      tailf:display-when "not(../../ncs-internal:module) or ../../ncs-internal:module[ncs-internal:name='tailf-ncs-netconf-ned-builder'] or (../../ncs-internal:live-status-protocol[not(ncs-internal:capability)]) or (../../ncs-internal:live-status-protocol/ncs-internal:capability/ncs-internal:module[.='tailf-ncs-netconf-ned-builder'])";
      tailf:hidden "tailf-devtools";
      description
        "Top container for the NETCONF NED builder data model. The container is
         invisible in the CLI, unless 'devtools' session parameter is set
         to 'true'.";

      grouping common-leafs {
        description
          "Common parameters for YANG modules and submodules.";
        leaf name {
          type yang:yang-identifier;
          description
            "The YANG module or submodule name.";
        }
        leaf revision {
          type union {
            type yanglib:live_ncs_revision-identifier;
            type string {
              length "0";
            }
          }
          description
            "The YANG module or submodule revision date.
             A zero-length string is used if no revision statement
             is present in the YANG module or submodule.";
        }
      }
      list project {
        key "family-name major-version";
        description
          "An instance of NED project. One project is associated with one device
           which is used as a reference device for the kind of devices the NED
           needs to be built. The key of the project is family-name and
           major-version that are used in the NED name.";
        leaf family-name {
          type string;
          description
            "NED family name";
        }
        leaf major-version {
          type ncs:live_ncs_package-version;
          description
            "NED major version";
        }
        leaf device {
          // NCS drop mandatory statement
          description
            "Reference device for the kind of devices the NED is built for.";
          type leafref {
            path "/ncs-internal:devices/ncs-internal:device/ncs-internal:live-status/ncs:devices/ncs:device/ncs:name" {
              tailf:xpath-root 3;
            }
          }
        }
        leaf local-user {
          // NCS drop mandatory statement
          type string;
          description
            "The NETCONF NED builder will authenticate to device with the
             credentials configured for this NSO user. It is adviced to not
             configure the 'same-pass' option for this user to communicate
             with the device, otherwise the NETCONF NED builder will not be
             able to communicate with the device when the configured user is
             not logged into NSO.";
        }
        leaf vendor {
          // NCS drop mandatory statement
          type string;
          description
            "Vendor field is a mandatory meta-data for the NED package, stored
             in the package-meta-data.xml.";
        }
        leaf max-download-threads {
          // NCS drop default statement
          type uint8;
          description
            "The NETCONF NED builder will download YANG models in multiple
             threads, and multiple NETCONF session will be open simultaneously
             towards the device corresponding to the number of threads. This
             value indicates the maximum number of download threads launched by
             this NETCONF NED builder project.";
        }
        leaf download-cache-path {
          // NCS drop tailf:cdb-oper
          type string;
          description
            "Leaf indicating the location of the cache path, populated by system.
             The modules in the cache MUST NOT be modified, but modules that are
             not possible to download may be copied into the cache directory.";
        }
        leaf ned-directory-path {
          // NCS drop tailf:cdb-oper
          type string;
          description
            "Leaf indicating the location of the current working NED,
             populated by system";
        }
        leaf build-status {
          // NCS drop tailf:cdb-oper
          type live_ncs_build-status-t;
          description
            "This leaf indicates whether the latest NED build has been
             successful.";
        }
        leaf build-error-info {
          // NCS drop when statement
          // NCS drop tailf:cdb-oper
          type string;
          description
            "If a NED build resulted in an error, this leaf will contain
             additional information.";
        }
        leaf compiler-output {
          tailf:hidden "debug";
          tailf:cli-preformatted;
          // NCS drop tailf:cdb-oper
          type string;
          description
            "This hidden leaf contains the full output of the compiler collected
             during the last build attempt.";
        }
        action fetch-module-list {
          tailf:actionpoint ncsproxy {
            tailf:internal;
          }
          description
            "This action initiates connection to the device and collects
             information about the supported data models from capabilities and
             ietf-yang-library data model, as well as schemas available through
             ietf-netconf-monitoring data model. The result of this action is
             stored in the 'module' list.";
          // NCS drop tailf:actionpoint
          input {
            must "deref(../../device)/device-type/ned-id = 'ned:netconf'" {
              tailf:xpath-root 3;
              tailf:dependency "../../device";
            }
            leaf overwrite {
              type empty;
              description
                "This leaf indiates that the list of modules should be re-fetched,
                 leading to the current selection status being reset and current
                 download cache being cleared.";
            }
          }
        }
        action build-ned {
          tailf:actionpoint ncsproxy {
            tailf:internal;
          }
          description
            "This action creates a minimal NED structure and runs the compiler
             to build the models for NSO. This NED does not have a netsim
             directory nor Makefile. It is adviced to avoid modifying such NED
             by manual intervention, but only by modifying the module selection in
             NSO and running this action again.

             In case of success the compiled NED is stored in NSO state and may
             be exported with the 'export-ned' action. In case of failure the NSO
             only keeps the compiler output in CDB (see 'build-warning' and
             'build-error' leafs on modules and submodules and 'compiler-output'
             hidden leaf), but the actual copy of the failed NED is deleted.

             In cases the NED might require more advanced intervention such as
             modification of YANG files or making a netsim device, it is adviced
             to make a development NED using 'make-development-ned' action.";
          // NCS drop tailf:actionpoint
          input {
            leaf overwrite {
              type empty;
              description
                "By default we will not overwrite an existing NED. This option
                 tells NSO to delete the existing copy of the NED and try again.";
            }
          }
        }
        action make-development-ned {
          tailf:actionpoint ncsproxy {
            tailf:internal;
          }
          description
            "This action creates a development NED package in the specified
             parent directory, but does not build it. The package needs to be
             built separately by running 'make' in its src/ subdirectory. The
             development NED package supports netsim and the user has the freedom
             of making modifications to the YANG files or build process.";
          // NCS drop tailf:actionpoint
          input {
            leaf in-directory {
              mandatory true;
              type live_ncs_dir-path-t;
              tailf:cli-completion-actionpoint dir-path-comp;
              description
                "The NED directory will be created as subdirectory to the
                 specified one. The user must have write access to the specified
                 directory.";
            }
            leaf overwrite {
              type empty;
              description
                "If the file with the generated name already exists in the
                 specified directory, then replace it with the new one.

                 If the file exists in the directory and this option is not
                 specified, then the action will fail.";
            }
          }
          output {
            leaf ned-path {
              mandatory true;
              type string;
              description
                "Absolute path to the generated NED directory.";
            }
          }
        }
        action export-ned {
          tailf:actionpoint ncsproxy {
            tailf:internal;
          }
          description
            "This action will export the NED previously built with 'build-ned'
             action in form of tarball. The action takes as input the target
             directory to write the tar-file into, and the actual file name is
             generated internally according to the naming convention
             'ncs-<version>-<ned family>-<ned version>.tar.gz'.";
          // NCS drop tailf:actionpoint
          input {
            leaf to-directory {
              mandatory true;
              type live_ncs_dir-path-t;
              tailf:cli-completion-actionpoint dir-path-comp;
              description
                "The tar file containing the NED will be created in the specified
                 directory. The user must have write access to the specified
                 directory.";
            }
            leaf overwrite {
              type empty;
              description
                "If the file with the generated name already exists in the
                 specified directory, then replace it with the new one.

                 If the file exists in the directory and this option is not
                 specified, then the action will fail.";
            }
          }
          output {
            leaf tar-file {
              mandatory true;
              type string;
              description
                "Absolute path to the generated tar file.";
            }
          }
        }
        action save-selection {
          tailf:actionpoint ncsproxy {
            tailf:internal;
          }
          description
            "Saves current selection with specified name under
             /netconf-ned-builder/profile list. The selection may be
             modified, exported into XML file and loaded on another system
             or reused to make similar NED.";
          // NCS drop tailf:actionpoint
          input {
            leaf profile {
              mandatory true;
              must 'not(/netconf-ned-builder/profile[name=current()])' {
                tailf:xpath-root 3;
              }
              type string;
              description
                "Name of the profile to save. The profile must not exist.";
            }
            leaf no-revisions {
              type empty;
              description
                "Save only module names as a profile, without revision data.";
            }
          }
        }

        grouping import-list {
          list import {
            key "name";
            uses common-leafs;
            description
              "List of import dependencies for this module or submodule
               containing imported module and possibly revision if this
               information is available.";
          }
        }

        grouping location-leaf-list {
          leaf-list location {
            type union {
              type enumeration {
                enum "NETCONF";
              }
              type inet:uri;
            }
            description
              "One or more locations from which the module or submodule can be
               retrieved.

               The special value 'NETCONF' means that the module or submodule is
               obtainable using NETCONF get-schema RPC.";
          }
        }

        grouping additional-info {
          leaf select-info {
            type string;
            description
              "This leaf provides additional information in case of errors
               selecting or downloading module.";
          }
          leaf build-warning {
            type string;
            tailf:cli-preformatted;
            description
              "This leaf contains compiler warnings related to this module,
               as printed by the compiler when building the NED.";
          }
          leaf build-error {
            type string;
            tailf:cli-preformatted;
            description
              "This leaf contains compiler errors related to this module,
               as printed by the compiler when building the NED.";
          }
        }
        list module {
          // NCS drop tailf:cdb-oper
          // NCS drop tailf:cli-allow-wildcard
          key "name revision";
          description
            "This list contains modules supported by the device as identified
             by fetch-module-list action.";
          // NCS expand uses statement
          leaf name {
            type yang:yang-identifier;
            description
              "The YANG module or submodule name.";
            // NCS drop tailf:cli-allow-range
          }
          leaf revision {
            type union {
              type yanglib:live_ncs_revision-identifier;
              type string {
                length "0";
              }
            }
            description
              "The YANG module or submodule revision date.
               A zero-length string is used if no revision statement
               is present in the YANG module or submodule.";
            // NCS drop tailf:cli-allow-range
          }
          leaf namespace {
            type inet:uri;
            // NCS drop mandatory statement
            description
              "The XML namespace identifier for this module.";
          }
          leaf-list feature {
            type yang:yang-identifier;
            description
              "List of YANG feature names from this module that are
               supported by the server, regardless of whether they are
               defined in the module or any included submodule.";
          }
          list deviation {
            key "name";
            uses common-leafs;
            description
              "List of deviation dependencies for this module containing
               deviation module and possibly revision if this information
               is available.";
          }
          uses import-list;
          uses location-leaf-list;
          list submodule {
            key "name revision";
            description
              "This list contains submodules belonging to the module as
               identified by fetch-module-list action.";
            uses common-leafs;
            uses import-list;
            uses location-leaf-list;
            leaf status {
              type live_ncs_submodule-status-t;
              description
                "Download status of the submodule";
            }
            uses additional-info;
          }
          leaf status {
            type live_ncs_module-status-t;
            description
              "Selection and download status of the module";
          }
          uses additional-info;
          action select {
            tailf:actionpoint ncsproxy {
              tailf:internal;
            }
            description
              "Select module for including in the NED. Selecting the module
               automatically starts download of the module and all of its
               submodules in background. Certain other dependencies are also
               selected by default, see option 'no-dependencies' below.";
            // NCS drop tailf:actionpoint
            input {
              leaf no-dependencies {
                type empty;
                description
                  "Do not select module's dependencies automatically. By default
                   known deviations and impored modules are automatically
                   selected. This option is useful for scripting.

                   Submodules are always selected if there are any, regardless
                   of this option being set.";
              }
            }
          }
          action deselect {
            tailf:actionpoint ncsproxy {
              tailf:internal;
            }
            description
              "Deselecting the module removes the selection mark, but does not
               remove the YANG file if it has already been downloaded.
               A deselected module is not included in the NED.

               Unlike action 'select', this action does not check the
               dependencies between the modules. It only deselects this module
               and its submodules, but not any modules depending on it.";
            // NCS drop tailf:actionpoint
          }
        }
      }
      list profile {
        key "name";
        description
          "This list contains profiles, which are reusable selections of
           modules. The module name is mandatory, while the revision is
           optional which makes it possible to reuse between different device
           versions, e.g. to generate a new version of the NED for
           the upgraded device.";
        leaf name {
          type string;
          description
            "The name of the profile.";
        }
        list module {
          key "name";
          // NCS expand uses statement
          leaf name {
            type yang:yang-identifier;
            description
              "The YANG module or submodule name.";
          }
          leaf revision {
            type union {
              type yanglib:live_ncs_revision-identifier;
              type string {
                length "0";
              }
            }
            description
              "The revision is optional in the profile. If unset, then
               applying the profile will select the module with the
               matching name and any revision.";
          }
        }
        action apply {
          tailf:actionpoint ncsproxy {
            tailf:internal;
          }
          description
            "Select the set of modules defined by this profile in the project
             indicated by the input parameters.";
          // NCS drop tailf:actionpoint
          input {
            leaf family-name {
              mandatory true;
              type leafref {
                path "/ncs-internal:devices/ncs-internal:device/ncs-internal:live-status/netconf-ned-builder/project/family-name" {
                  tailf:xpath-root 3;
                }
              }
              description
                "Reference to the target project's family-name.";
            }
            leaf major-version {
              mandatory true;
              type leafref {
                path "/ncs-internal:devices/ncs-internal:device/ncs-internal:live-status/netconf-ned-builder/project[family-name=current()/../family-name]/major-version" {
                  tailf:xpath-root 3;
                }
              }
              description
                "Reference to the target project's major-version.";
            }
            leaf best-effort {
              type empty;
              description
                "Skip modules that do not exist in the project.";
            }
            leaf with-dependencies {
              type empty;
              description
                "By default the list of modules configured in a profile is
                 assumed to be exhaustive so the dependencies for the selected
                 modules are not selected. This option allows to select modules
                 specified by the profile and automatically select their
                 dependencies.";
            }
          }
          output {
            leaf result {
              type enumeration {
                enum "applied";
                enum "not-applied";
              }
              description
                "The result of the profile application.";
            }
            leaf-list selected {
              type string;
              description
                "The list of names of the successfully selected modules.";
            }
            leaf-list not-found {
              type string;
              description
                "The list of names of the modules that were not found in the
                 target project.";
            }
            leaf-list ambiguous {
              type string;
              description
                "The list of names of the modules that were found in more than
                 one instance in the target project.";
            }
          }
        }
      }
    }
  }
  augment "/ncs-internal:devices/ncs-internal:template/ncs-internal:ned-id/ncs-internal:config" {
    container netconf-ned-builder {
      tailf:hidden "tailf-devtools";
      description
        "Top container for the NETCONF NED builder data model. The container is
         invisible in the CLI, unless 'devtools' session parameter is set
         to 'true'.";

      grouping common-leafs {
        description
          "Common parameters for YANG modules and submodules.";
        leaf name {
          type string;
          description
            "The YANG module or submodule name.";
        }
        leaf revision {
          type string;
          description
            "The YANG module or submodule revision date.
             A zero-length string is used if no revision statement
             is present in the YANG module or submodule.";
        }
      }
      list project {
        // NCS patched for predictable order
        ordered-by user;
        key "family-name major-version";
        description
          "An instance of NED project. One project is associated with one device
           which is used as a reference device for the kind of devices the NED
           needs to be built. The key of the project is family-name and
           major-version that are used in the NED name.";
        leaf family-name {
          type string;
          description
            "NED family name";
        }
        leaf major-version {
          type ncs:ncs_template_package-version;
          description
            "NED major version";
        }
        leaf device {
          // NCS drop mandatory statement
          description
            "Reference device for the kind of devices the NED is built for.";
          type string;
        }
        leaf local-user {
          // NCS drop mandatory statement
          type string;
          description
            "The NETCONF NED builder will authenticate to device with the
             credentials configured for this NSO user. It is adviced to not
             configure the 'same-pass' option for this user to communicate
             with the device, otherwise the NETCONF NED builder will not be
             able to communicate with the device when the configured user is
             not logged into NSO.";
        }
        leaf vendor {
          // NCS drop mandatory statement
          type string;
          description
            "Vendor field is a mandatory meta-data for the NED package, stored
             in the package-meta-data.xml.";
        }
        leaf max-download-threads {
          // NCS drop default statement
          type string;
          description
            "The NETCONF NED builder will download YANG models in multiple
             threads, and multiple NETCONF session will be open simultaneously
             towards the device corresponding to the number of threads. This
             value indicates the maximum number of download threads launched by
             this NETCONF NED builder project.";
        }
        // NCS drop config false leaf 'download-cache-path'
        // NCS drop config false leaf 'ned-directory-path'
        // NCS drop config false leaf 'build-status'
        // NCS drop config false leaf 'build-error-info'
        // NCS drop config false leaf 'compiler-output'

        grouping import-list {
          list import {
            // NCS patched for predictable order
            ordered-by user;
            key "name";
            uses common-leafs;
            description
              "List of import dependencies for this module or submodule
               containing imported module and possibly revision if this
               information is available.";
          }
        }

        grouping location-leaf-list {
          leaf-list location {
            // NCS patched for predictable order
            ordered-by user;
            type string;
            description
              "One or more locations from which the module or submodule can be
               retrieved.

               The special value 'NETCONF' means that the module or submodule is
               obtainable using NETCONF get-schema RPC.";
          }
        }

        grouping additional-info {
          leaf select-info {
            type string;
            description
              "This leaf provides additional information in case of errors
               selecting or downloading module.";
          }
          leaf build-warning {
            type string;
            description
              "This leaf contains compiler warnings related to this module,
               as printed by the compiler when building the NED.";
          }
          leaf build-error {
            type string;
            description
              "This leaf contains compiler errors related to this module,
               as printed by the compiler when building the NED.";
          }
        }
        // NCS drop config false list module
      }
      list profile {
        // NCS patched for predictable order
        ordered-by user;
        key "name";
        description
          "This list contains profiles, which are reusable selections of
           modules. The module name is mandatory, while the revision is
           optional which makes it possible to reuse between different device
           versions, e.g. to generate a new version of the NED for
           the upgraded device.";
        leaf name {
          type string;
          description
            "The name of the profile.";
        }
        list module {
          // NCS patched for predictable order
          ordered-by user;
          key "name";
          // NCS expand uses statement
          leaf name {
            type string;
            description
              "The YANG module or submodule name.";
          }
          leaf revision {
            type string;
            description
              "The revision is optional in the profile. If unset, then
               applying the profile will select the module with the
               matching name and any revision.";
          }
        }
      }
    }
  }
}
