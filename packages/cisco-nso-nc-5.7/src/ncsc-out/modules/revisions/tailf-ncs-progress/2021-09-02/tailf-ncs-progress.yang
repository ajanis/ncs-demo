module tailf-ncs-progress {
  // Generated by yanger -t ncs
  tailf:mount-id "cisco-nso-nc-5.7:cisco-nso-nc-5.7";
  tailf:ncs-device-type "netconf";

  namespace "http://tail-f.com/ns/ncs-progress";
  prefix ncs-progress;

  import ietf-yang-types {
    prefix yang;
  }
  import tailf-progress {
    prefix progress;
  }
  import tailf-common {
    prefix tailf;
  }
  import tailf-ncs {
    prefix ncs;
  }
  import tailf-ncs-internal-mount {
    prefix ncs-internal;
  }

  description
    "This module contains a collection of YANG definitions for
     tracing progress in NCS.

     Copyright 2018-2021 Cisco Systems, Inc.
     All rights reserved.
     Permission is hereby granted to redistribute this file without
     modification.";

  revision 2021-09-02 {
    description
      "Released as part of NCS-5.6.

       Added /progress/trace/event/package.

       Added enum 'create-subscription' to
       /progress/trace/event/device-phase.";
  }
  revision 2020-06-25 {
    description
      "Released as part of NCS-5.4.

       Added /progress/trace/debug.";
  }
  revision 2019-06-27 {
    description
      "Released as part of NCS-5.2.

       Added /progress/trace/event/package.

       Added enum 'show-offline', 'show-stats', 'show-stats-list',
       'is-alive', 'keep-alive', 'reconnect', and 'cmd' to
       /progress/trace/event/device-phase.";
  }
  revision 2018-11-12 {
    description
      "Released as part of NCS-4.7.2.

       Made leaf /progress/trace/event/service to not require instance.";
  }
  revision 2018-06-21 {
    description
      "Released as part of NCS-4.7.

       Added display-groups to some nodes.";
  }
  revision 2018-03-01 {
    description
      "Released as part of NCS-4.6.

       Initial revision.";
  }

  augment "/ncs-internal:devices/ncs-internal:template/ncs-internal:ned-id/ncs-internal:config/progress:progress/progress:trace" {
    leaf-list debug {
      // NCS patched for predictable order
      ordered-by user;
      description
        "Additional debug tracing. These are consciously left out of the
         normal debug level due to the high amount of output.
         Use with care.";
      type string;
    }
  }
  augment "/ncs-internal:devices/ncs-internal:device/ncs-internal:live-status/progress:progress/progress:trace" {
    leaf-list debug {
      tailf:ncs-device-type "netconf";
      tailf:display-when "not(../../ncs-internal:module) or ../../ncs-internal:module[ncs-internal:name='tailf-ncs-progress'] or (../../ncs-internal:live-status-protocol[not(ncs-internal:capability)]) or (../../ncs-internal:live-status-protocol/ncs-internal:capability/ncs-internal:module[.='tailf-ncs-progress'])";
      description
        "Additional debug tracing. These are consciously left out of the
         normal debug level due to the high amount of output.
         Use with care.";
      type enumeration {
        enum "xpath" {
          description
            "Detailed output from the XPath evaluator.";
        }
        enum "kicker" {
          description
            "Detailed output from data kicker evaluation.";
        }
        enum "subscriber" {
          description
            "Detailed output from CDB subscribers.";
        }
      }
    }
  }
  augment "/ncs-internal:devices/ncs-internal:device/ncs-internal:config/progress:progress/progress:trace" {
    leaf-list debug {
      tailf:ncs-device-type "netconf";
      tailf:display-when "not(../../ncs-internal:module) or ../../ncs-internal:module[ncs-internal:name='tailf-ncs-progress']";
      description
        "Additional debug tracing. These are consciously left out of the
         normal debug level due to the high amount of output.
         Use with care.";
      type enumeration {
        enum "xpath" {
          description
            "Detailed output from the XPath evaluator.";
        }
        enum "kicker" {
          description
            "Detailed output from data kicker evaluation.";
        }
        enum "subscriber" {
          description
            "Detailed output from CDB subscribers.";
        }
      }
    }
  }
  augment "/ncs-internal:devices/ncs-internal:template/ncs-internal:ned-id/ncs-internal:config/progress:progress/progress:trace/progress:filter" {
    choice object {
      case service {
        leaf all-services {
          type empty;
          description
            "Only log events for services.";
        }
        leaf service-type {
          type string;
          description
            "Only log events for the specified service type.";
        }
      }
      case device {
        choice device-choice {
          leaf all-devices {
            type empty;
            description
              "Only log events for devices.";
          }
          leaf device-group {
            type string;
            description
              "Only log events for devices in this group.";
          }
          leaf-list device {
            // NCS patched for predictable order
            ordered-by user;
            type string;
            description
              "Only log events for the specified device(s).";
          }
        }
      }
    }
  }
  augment "/ncs-internal:devices/ncs-internal:device/ncs-internal:live-status/progress:progress/progress:trace/progress:filter" {
    choice object {
      case service {
        leaf all-services {
          type empty;
          description
            "Only log events for services.";
        }
        leaf service-type {
          type tailf:node-instance-identifier;
          // NCS drop tailf:cli-completion-actionpoint
          description
            "Only log events for the specified service type.";
        }
      }
      case device {
        choice device-choice {
          leaf all-devices {
            type empty;
            description
              "Only log events for devices.";
          }
          leaf device-group {
            type string;
            tailf:non-strict-leafref {
              path "/ncs-internal:devices/ncs-internal:device/ncs-internal:live-status/ncs:devices/ncs:device-group/ncs:name" {
                tailf:xpath-root 3;
              }
            }
            description
              "Only log events for devices in this group.";
          }
          leaf-list device {
            type string;
            tailf:non-strict-leafref {
              path "/ncs-internal:devices/ncs-internal:device/ncs-internal:live-status/ncs:devices/ncs:device/ncs:name" {
                tailf:xpath-root 3;
              }
            }
            description
              "Only log events for the specified device(s).";
          }
        }
      }
    }
  }
  augment "/ncs-internal:devices/ncs-internal:device/ncs-internal:config/progress:progress/progress:trace/progress:filter" {
    choice object {
      case service {
        leaf all-services {
          type empty;
          description
            "Only log events for services.";
        }
        leaf service-type {
          type tailf:node-instance-identifier;
          tailf:cli-completion-actionpoint servicepoints;
          description
            "Only log events for the specified service type.";
        }
      }
      case device {
        choice device-choice {
          leaf all-devices {
            type empty;
            description
              "Only log events for devices.";
          }
          leaf device-group {
            type string;
            tailf:non-strict-leafref {
              path "/ncs-internal:devices/ncs-internal:device/ncs-internal:config/ncs:devices/ncs:device-group/ncs:name" {
                tailf:xpath-root 3;
              }
            }
            description
              "Only log events for devices in this group.";
          }
          leaf-list device {
            type string;
            tailf:non-strict-leafref {
              path "/ncs-internal:devices/ncs-internal:device/ncs-internal:config/ncs:devices/ncs:device/ncs:name" {
                tailf:xpath-root 3;
              }
            }
            description
              "Only log events for the specified device(s).";
          }
        }
      }
    }
  }
  augment "/ncs-internal:devices/ncs-internal:device/ncs-internal:live-status/progress:progress/progress:trace/progress:event" {
    leaf service {
      tailf:ncs-device-type "netconf";
      tailf:display-when "not(../../ncs-internal:module) or ../../ncs-internal:module[ncs-internal:name='tailf-ncs-progress'] or (../../ncs-internal:live-status-protocol[not(ncs-internal:capability)]) or (../../ncs-internal:live-status-protocol/ncs-internal:capability/ncs-internal:module[.='tailf-ncs-progress'])";
      // NCS drop tailf:display-groups
      // NCS patched to string, due to LSA partial NED
      type string;
      description
        "The invoked service instance.";
    }
    leaf service-phase {
      tailf:ncs-device-type "netconf";
      tailf:display-when "not(../../ncs-internal:module) or ../../ncs-internal:module[ncs-internal:name='tailf-ncs-progress'] or (../../ncs-internal:live-status-protocol[not(ncs-internal:capability)]) or (../../ncs-internal:live-status-protocol/ncs-internal:capability/ncs-internal:module[.='tailf-ncs-progress'])";
      // NCS drop tailf:display-groups
      type enumeration {
        enum "pre-modification";
        enum "pre-lock-create";
        enum "create";
        enum "post-modification";
      }
      description
        "The callback phase of the invoked service instance.";
    }
    leaf commit-queue-id {
      tailf:ncs-device-type "netconf";
      tailf:display-when "not(../../ncs-internal:module) or ../../ncs-internal:module[ncs-internal:name='tailf-ncs-progress'] or (../../ncs-internal:live-status-protocol[not(ncs-internal:capability)]) or (../../ncs-internal:live-status-protocol/ncs-internal:capability/ncs-internal:module[.='tailf-ncs-progress'])";
      // NCS drop tailf:display-groups
      type uint64;
      description
        "The commit queue item id.";
    }
    leaf node {
      tailf:ncs-device-type "netconf";
      tailf:display-when "not(../../ncs-internal:module) or ../../ncs-internal:module[ncs-internal:name='tailf-ncs-progress'] or (../../ncs-internal:live-status-protocol[not(ncs-internal:capability)]) or (../../ncs-internal:live-status-protocol/ncs-internal:capability/ncs-internal:module[.='tailf-ncs-progress'])";
      // NCS drop tailf:display-groups
      type ncs:live_ncs_node-name;
      tailf:non-strict-leafref {
        path "/ncs-internal:devices/ncs-internal:device/ncs-internal:live-status/ncs:cluster/ncs:remote-node/ncs:name" {
          tailf:xpath-root 3;
        }
      }
    }
    leaf device {
      tailf:ncs-device-type "netconf";
      tailf:display-when "not(../../ncs-internal:module) or ../../ncs-internal:module[ncs-internal:name='tailf-ncs-progress'] or (../../ncs-internal:live-status-protocol[not(ncs-internal:capability)]) or (../../ncs-internal:live-status-protocol/ncs-internal:capability/ncs-internal:module[.='tailf-ncs-progress'])";
      // NCS drop tailf:display-groups
      type string;
      tailf:non-strict-leafref {
        path "/ncs-internal:devices/ncs-internal:device/ncs-internal:live-status/ncs:devices/ncs:device/ncs:name" {
          tailf:xpath-root 3;
        }
      }
    }
    leaf device-phase {
      tailf:ncs-device-type "netconf";
      tailf:display-when "not(../../ncs-internal:module) or ../../ncs-internal:module[ncs-internal:name='tailf-ncs-progress'] or (../../ncs-internal:live-status-protocol[not(ncs-internal:capability)]) or (../../ncs-internal:live-status-protocol/ncs-internal:capability/ncs-internal:module[.='tailf-ncs-progress'])";
      // NCS drop tailf:display-groups
      type enumeration {
        enum "noconnect";
        enum "connect";
        enum "initialize";
        enum "uninitialize";
        enum "prepare";
        enum "abort";
        enum "commit";
        enum "revert";
        enum "persist";
        enum "close";
        enum "get-trans-id";
        enum "show";
        enum "show-partial";
        enum "scp";
        enum "show-offline";
        enum "show-stats";
        enum "show-stats-list";
        enum "show-stats-path";
        enum "is-alive";
        enum "keep-alive";
        enum "reconnect";
        enum "cmd";
        enum "create-subscription";
      }
      description
        "The device communication phase.";
    }
    leaf package {
      tailf:ncs-device-type "netconf";
      tailf:display-when "not(../../ncs-internal:module) or ../../ncs-internal:module[ncs-internal:name='tailf-ncs-progress'] or (../../ncs-internal:live-status-protocol[not(ncs-internal:capability)]) or (../../ncs-internal:live-status-protocol/ncs-internal:capability/ncs-internal:module[.='tailf-ncs-progress'])";
      // NCS drop tailf:display-groups
      type string;
    }
  }
}
