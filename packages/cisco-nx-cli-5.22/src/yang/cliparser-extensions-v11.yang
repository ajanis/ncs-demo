// Global nedcom cli parser extensions
// NOTE: Original of this file resides in nedcom, don't edit local copy in ned.

module cliparser-extensions-v11 {
  namespace "http://tail-f.com/ned/cliparser_v11";
  prefix cli;

  //
  // Yang syntax extension statements
  //
  extension builtin {
    argument value;
    cli:builtin "true";
  }

  extension direction {
    cli:builtin "true";
    argument value;
  }

  extension state {
    cli:builtin "true";
    argument value;
  }

  extension arguments {
    cli:builtin "true";
    argument value;
  }

  extension json-arguments {
    cli:builtin "true";
    argument value;
  }

  extension callback {
    cli:builtin "true";
    argument value;
  }

  extension module-meta-data {
    cli:builtin "true";
  }

  extension java-callback-method {
    cli:builtin "true";
    argument value;
  }


  // Cli parser builtins
  //
  extension parse-compact-syntax {
    cli:builtin "true";
  }
  extension parse-relaxed-syntax {
    cli:builtin "true";
  }
  extension parse-global-when {
    cli:builtin "true";
  }
  extension parse-inline-when {
    cli:builtin "true";
  }
  extension parse-alt-name {
    cli:builtin "true";
    argument value;
  }
  extension parse-alt-regex {
    cli:builtin "true";
    argument value;
  }
  extension parse-no-auto-match {
    cli:builtin "true";
  }
  extension parse-disallow-type {
    cli:builtin "true";
    argument value;
  }
  extension parse-match-prefix {
    cli:builtin "true";
  }
  extension diff-dependency {
    cli:builtin "true";
    cli:state "none";
    argument value;
  }
  extension diff-explicit-choice {
    cli:builtin "true";
    cli:state "none";
    argument value;
  }
  extension diff-delete-before {
    cli:builtin "true";
    cli:state "none";
    argument value;
  }
  extension diff-delete-after {
    cli:builtin "true";
    cli:state "none";
    argument value;
  }
  extension diff-set-before {
    cli:builtin "true";
    cli:state "none";
    argument value;
  }
  extension diff-set-after {
    cli:builtin "true";
    cli:state "none";
    argument value;
  }
  extension when-target-delete {
    cli:builtin "true";
    cli:state "none";
  }
  extension when-target-set {
    cli:builtin "true";
    cli:state "none";
  }
  extension compact-need-when-eval {
    cli:builtin "true";
  }
  extension forced-when-eval-in-path {
    cli:builtin "true";
    argument value;
  }
  extension forced-relaxed-parse-in-path {
    cli:builtin "true";
    argument value;
  }

  // Extensions implemented in nedcom package
  //
  extension context-value-inject {
    //
    // Used in leaf nodes inside a context to inject values into context
    // (e.g. hidden defaults which are dynamic). This extension is called when
    // parser direction is FROM_DEVICE. Values will be injected in the resulting
    // CLI config, when using either parseAndLoadXMLConfigStream() or
    // filterConfig() from NedComCliBase.
    //
    // The argument can be any of the following:
    //
    // 'static'  This indicates that the value to inject is a static (hard-coded
    //           in yang) value given with the cli:arguments substatement.
    //
    // 'default' In this case the value to inject is the default of the leaf
    //           itself.
    //
    // 'dynamic' This is the most flexible variant which takes the value to
    //           inject from another leaf in the data tree (i.e. which is
    //           present in the CLI lines parsed before this context is
    //           encountered). The path to the leaf from where to get the value
    //           is either absolute, or relative to the context (i.e. NOT to the
    //           leaf where the extension is present). It is given with the
    //           cli:arguments substatement.
    //
    // Example usage, if the below 'shutdown' leaf is contained within a list
    // (context) which has a key leaf 'ethernet' the 'shutdown' leaf will be
    // injected with value 'false' (i.e. 'no shutdown' since it's a boolean-no)
    // when the key contains a '.', but if the key does not contain a '.' the
    // value to be injected will be fetched (at parse time) from the value of
    // '../default/shutdown' (i.e. which must have been present/parsed before
    // parsing the line which enters the context containing this 'shutdown'
    // leaf). Note, in this case, the path to the leaf is relative to the
    // enclosing list, not the leaf with the 'context-value-inject' extension.
    //
    //    leaf shutdown {
    //      cli:context-value-inject "static" {
    //        cli:arguments "false";
    //        when "contains(ethernet, '.')";
    //      }
    //      cli:context-value-inject "dynamic" {
    //        cli:arguments "../default/shutdown";
    //        when "not(contains(ethernet, '.'))";
    //      }
    //      tailf:cli-boolean-no;
    //      type boolean;
    //    }
    //
    cli:direction "from-device";
    cli:state "enter-context";
    cli:java-callback-method "com.tailf.packages.ned.nedcom.NedComCliExtensions.contextValueInject";
    argument value;
  }

  extension context-value-set-default {
    //
    // Same semantics as 'context-value-inject' but no cli-lines are injected,
    // instead values are only set upon last-exit-context if not set in context
    // (e.g. to explicitly set hidden defaults). This also allows for when-expr
    // on extension including values set in context (unlike when using
    // 'context-value-inject' which is run/evaluated on context-enter).
    //
    cli:direction "from-device";
    cli:state "last-exit-context";
    cli:java-callback-method "com.tailf.packages.ned.nedcom.NedComCliExtensions.contextValueInject";
    argument value;
  }

  //
  extension shutdown-before-edit {
    cli:direction "to-device";
    cli:state "post-match";
    cli:java-callback-method "com.tailf.packages.ned.nedcom.NedComCliExtensions.shutdownBeforeEdit";
    argument value;
  }

  extension globally-unique-value {
    cli:direction "to-device";
    cli:state "post-match|parent-context-deleted";
    cli:java-callback-method "com.tailf.packages.ned.nedcom.NedComCliExtensions.globallyUniqueValue";
    argument value;
  }

  extension split-chunk {
    cli:direction "to-device";
    cli:state "post-match";
    cli:java-callback-method "com.tailf.packages.ned.nedcom.NedComCliExtensions.splitChunk";
    argument value; // "before" or "after"
  }

  // CDB backwards compatible custom extension "cli:secret" meta-data replacement
  extension secret {
    cli:direction "both";
    cli:state "post-match";
    cli:java-callback-method "com.tailf.packages.ned.nedcom.NedComCliExtensions.secret";
  }

  extension delete-with-default {
    cli:direction "to-device";
    cli:state "post-match";
    cli:java-callback-method "com.tailf.packages.ned.nedcom.NedComCliExtensions.deleteWith";
  }

  extension trim-delete {
    cli:direction "to-device";
    cli:state "post-match";
    cli:java-callback-method "com.tailf.packages.ned.nedcom.NedComCliExtensions.deleteWith";
  }

  extension trim-delete-if-match {
    argument value; // <regex>
    cli:direction "to-device";
    cli:state "post-match";
    cli:java-callback-method "com.tailf.packages.ned.nedcom.NedComCliExtensions.deleteWith";
  }

  extension custom-delete {
    argument value; // <custom command line>
    cli:direction "to-device";
    cli:state "post-match";
    cli:java-callback-method "com.tailf.packages.ned.nedcom.NedComCliExtensions.deleteWith";
  }

  extension multi-line-banner {
    cli:direction "both";
    cli:state "multi-line";
    cli:java-callback-method "com.tailf.packages.ned.nedcom.NedComCliExtensions.multiLineBanner";
    //
    // Uses cli:json-arguments:
    //
    //   delimiter: Character to use for delimiter when rendering multi-line
    //              output (if not saved in a leaf, see below) (i.e. inferred on
    //              input, doesn't need to be same)
    //
    //   eol: End of line, string to append to each line e.g. "\r\n", default if
    //        not given is "\n"
    //
    // When used in container:
    //
    //   text: Child node in container to put banner text in
    //
    //   start-delim: schema node to use for saving start delimiter character
    //                (can be left out if delimiter is given)
    //
    //   end-delim: schema node to use for saving end delimiter character
    //              (optional, not used except for storage, start/end delimiter
    //              assumed to be same)
    //
    // NOTE: If NED uses parseCLIDiff() the resulting output is rendered, as it
    // would be entered on device, enclosed in comment-lines marking start/end of
    // banner,like this:
    //
    //  ! MULTI_LINE_BANNER START
    //  banner motd ^Multi line
    //  text containing banner here^
    //  ! MULTI_LINE_BANNER END\n" +
    //
    // Example usage in leaf:
    //
    //   container banner {
    //     leaf motd {
    //       tailf:cli-no-value-on-delete;
    //       cli:multi-line-banner {
    //         cli:json-arguments '{"delimiter":"^", "eol":"\r\n" }';
    //       }
    //       type string;
    //     }
    //   }
    //
    // Example usage in leaf:
    //
    //   container motd {
    //     tailf:cli-sequence-commands;
    //     tailf:cli-compact-syntax;
    //     cli:multi-line-banner '{ "text":"message", "start-delim":"start-maker", "end-delim":"end-maker" }';
    //     leaf start-marker {
    //       tailf:cli-drop-node-name;
    //       tailf:cli-no-value-on-delete;
    //       type string;
    //     }
    //     leaf message {
    //       tailf:cli-drop-node-name;
    //       tailf:cli-no-value-on-delete;
    //       type string;
    //     }
    //     leaf end-marker {
    //       tailf:cli-drop-node-name;
    //       tailf:cli-no-value-on-delete;
    //       type string;
    //     }
    //   }
    //
  }

  extension ned-diff-add {
    cli:direction "to-device";
    cli:state "post-match|parent-context-deleted";
    cli:java-callback-method "com.tailf.packages.ned.nedcom.NedDiffCliExtensions.add";
  }

  extension ned-diff-move-first {
    cli:direction "to-device";
    cli:state "post-match|parent-context-deleted";
    cli:java-callback-method "com.tailf.packages.ned.nedcom.NedDiffCliExtensions.moveFirst";
  }

  extension ned-diff-move-last {
    cli:direction "to-device";
    cli:state "post-match|parent-context-deleted";
    cli:java-callback-method "com.tailf.packages.ned.nedcom.NedDiffCliExtensions.moveLast";
  }

  extension ned-diff-move-after {
    argument value; // <target regex>
    cli:direction "to-device";
    cli:state "post-match|parent-context-deleted";
    cli:java-callback-method "com.tailf.packages.ned.nedcom.NedDiffCliExtensions.moveAfter";
  }

  extension ned-diff-move-before {
    argument value; // <target regex>
    cli:direction "to-device";
    cli:state "post-match|parent-context-deleted";
    cli:java-callback-method "com.tailf.packages.ned.nedcom.NedDiffCliExtensions.moveBefore";
  }

  extension ned-diff-stay-after {
    argument value; // <target regex>
    cli:direction "to-device";
    cli:state "post-match|parent-context-deleted";
    cli:java-callback-method "com.tailf.packages.ned.nedcom.NedDiffCliExtensions.stayAfter";
  }

  extension ned-diff-stay-before {
    argument value; // <target regex>
    cli:direction "to-device";
    cli:state "post-match|parent-context-deleted";
    cli:java-callback-method "com.tailf.packages.ned.nedcom.NedDiffCliExtensions.stayBefore";
  }

}
