module tailf-ned-secrets {
  namespace 'http://tail-f.com/ned/ned-secrets';
  prefix secrets;

  import tailf-common {
    prefix tailf;
  }
  import tailf-ncs {
    prefix ncs;
  }

  revision 2019-04-17 {
    description
      "Second version";
  }

  augment "/ncs:devices/ncs:device/ncs:ned-settings" {
    container secrets {
      tailf:info "NedSecrets oper data. Do not modify";
      config false;
      tailf:cdb-oper {
        tailf:persistent true;
      }

      // secrets secret *
      list secret {
        tailf:cli-suppress-mode;
        tailf:cli-delete-when-empty;
        key id;
        leaf id {
          type string;
        }
        leaf encrypted {
          type string;
        }
        leaf cleartext {
          tailf:hidden all;
          type string;
        }
        leaf regex {
          //tailf:hidden all;
          type string;
        }
        leaf alwaysEncrypted {
          tailf:hidden all;
          type string;
        }
      }
    }
  }

}
