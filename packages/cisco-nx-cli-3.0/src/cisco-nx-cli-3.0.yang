module cisco-nx-cli-3.0 {
  yang-version 1.1;
  namespace "http://tail-f.com/ns/ned-id/cisco-nx-cli-3.0";
  prefix cisco-nx-cli-3.0;

  import cisco-nx-cli {
    prefix family;
  }

  identity cisco-nx-cli-3.0 {
    base family:cisco-nx-cli;
  }
}
