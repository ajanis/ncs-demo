module access {
  namespace "http://com/example/access";
  prefix access;

  import ietf-inet-types {
    prefix inet;
  }
  import tailf-ncs {
    prefix ncs;
  }

  list access {
    key customer-name;

    uses ncs:service-data;
    ncs:servicepoint "access";

    leaf customer-name {
      type string;
    }

    leaf-list device {
      type leafref {
        path "/ncs:devices/ncs:device/ncs:name";
      }
    }

    leaf vlan {
      mandatory true;
      type uint16;
    }

    leaf trunk-interface {
      mandatory true;
      type string;
    }

    leaf access-interface-type {
        mandatory true;
        type string;
    }

    leaf access-interface-id {
      mandatory true;
      type string;
    }
  }
}
