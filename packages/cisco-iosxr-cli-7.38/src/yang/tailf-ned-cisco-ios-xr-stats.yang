module tailf-ned-cisco-ios-xr-stats {
  namespace 'http://tail-f.com/ned/cisco-ios-xr-stats';
  prefix cisco-ios-xr-stats;

  import tailf-common {
    prefix tailf;
  }


  // =========================================================================
  //                        LIVE-STATUS
  // =========================================================================

  // show devices device <devname> live-status inventory
  list inventory {
    tailf:info "show inventory";
    tailf:meta-data "ned-livestats:parser-info" {
      tailf:meta-value "{'template':'inventory.gili','show':'show inventory'}";
    }
    config false;
    key name;
    leaf name {
      type string;
    }
    leaf descr {
      type string;
    }
    leaf pid {
      type string;
    }
    leaf vid {
      type string;
    }
    leaf sn {
      type string;
    }
  }


  /// ========================================================================
  /// cdp
  /// ========================================================================

  // cdp neighbors *
  container cdp {
    tailf:info "show cdp";
    config false;
    list neighbors {
      tailf:info "show cdp neighbors detail";
      tailf:meta-data "ned-livestats:parser-info" {
        tailf:meta-value "{'template':'cdp_neighbors.gili','show':'show cdp neighbors detail'}";
      }
      key local-interface;
      leaf local-interface {
        type string;
      }
      leaf device-id {
        type string;
      }
      leaf hold-time {
        type string;
      }
      leaf capability {
        type string;
      }
      leaf platform {
        type string;
      }
      leaf port-id {
        type string;
      }
    }
  }


  /// ========================================================================
  /// lldp
  /// ========================================================================

  // lldp neighbors *
  container lldp {
    tailf:info "show lldp";
    config false;
    list neighbors {
      tailf:info "show lldp neighbors detail";
      tailf:meta-data "ned-livestats:parser-info" {
        tailf:meta-value "{'template':'lldp_neighbors.gili','show':'show lldp neighbors detail'}";
      }
      key local-interface;
      leaf local-interface {
        type string;
      }
      leaf parent-interface {
        type string;
      }
      leaf device-id {
        type string;
      }
      leaf time-remaining {
        type string;
      }
      leaf hold-time {
        type string;
      }
      leaf capability {
        type string;
      }
      leaf chassis-id {
        type string;
      }
      leaf port-id {
        type string;
      }
    }
  }

  /// ========================================================================
  /// controllers
  /// ========================================================================

  // controllers Optics *
  container controllers {
    tailf:info "Interface controller status and configuration";
    config false;
    list Optics {
      tailf:info "OPTICS controller | short name is Op";
      tailf:meta-data "ned-livestats:parser-info" {
        tailf:meta-value "{'template':'controllers-optics.gili','show':'show run all-interfaces | include Optics'}";
      }
      key id;
      leaf id {
        type string;
      }
      container instance {
        tailf:cli-drop-node-name;
        presence true;
        tailf:meta-data "ned-livestats:parser-info" {
          tailf:meta-value "{'template':'controllers-optics-instance.gili','show':'show controllers Optics %s'}";
        }
        leaf controller-state {
          type string;
        }
        container transceiver-vendor-details {
          leaf form-factor {
            type string;
          }
          leaf optics-type {
            type string;
          }
          leaf name {
            type string;
          }
          leaf oui-number {
            type string;
          }
          leaf part-number {
            type string;
          }
          leaf rev-number {
            type string;
          }
          leaf serial-number {
            type string;
          }
          leaf pid {
            type string;
          }
          leaf vid {
            type string;
          }
          leaf date-code {
            type string;
          }
        }
      }
    }
  }

  /// ========================================================================
  /// exec
  /// ========================================================================

  container exec {
    tailf:info "Execute commands on device";

    // any [arg 1] .. [arg N]
    tailf:action any {
      tailf:info "Execute any command on device";
      tailf:actionpoint ncsinternal {
        tailf:internal;
      }
      input {
        leaf admin-mode {
          tailf:info "Set to run the action in admin mode";
          type empty;
        }
        list auto-prompts {
          tailf:info "One-shot auto-prompts list, used to ignore/reply on questions";
          tailf:cli-suppress-mode;
          key question;
          leaf question {
            tailf:info "Device question, regular expression";
            type string {
              tailf:info "WORD;;Question, regex format";
            }
          }
          leaf answer {
            tailf:info "Answer to device question";
            type string {
              tailf:info "WORD;;Answer to device question | <exit|prompt|timeout|ignore|enter>";
            }
          }
        }
        leaf-list args {
          tailf:cli-drop-node-name;
          tailf:cli-flat-list-syntax;
          type string {
            tailf:info "WORD;;any \"<cmd> [option(s)]\", e.g: any \"show ppp summary\"";
          }
        }
      }
      output {
        leaf result {
          type string;
        }
      }
    }

    // any-hidden [arg 1] .. [arg N]
    tailf:action any-hidden {
      tailf:info "Same as 'any' action except that nothing will be logged.";
      tailf:actionpoint ncsinternal {
        tailf:internal;
      }
      input {
        leaf admin-mode {
          tailf:info "Set to run the action in admin mode";
          type empty;
        }
        list auto-prompts {
          tailf:info "One-shot auto-prompts list, used to ignore/reply on questions";
          tailf:cli-suppress-mode;
          key question;
          leaf question {
            tailf:info "Device question, regular expression";
            type string {
              tailf:info "WORD;;Question, regex format";
            }
          }
          leaf answer {
            tailf:info "Answer to device question";
            type string {
              tailf:info "WORD;;Answer to device question | <exit|prompt|timeout|ignore|enter>";
            }
          }
        }
        leaf args {
          tailf:cli-drop-node-name;
          tailf:suppress-echo true;
          mandatory true;
          type string {
            tailf:info "WORD;;any \"<cmd> [option(s)]\", e.g: any \"show ppp summary\"";
          }
        }
      }
      output {
        leaf result {
          type string;
        }
      }
    }

    // show [arg 1] .. [arg N]
    tailf:action show {
      tailf:info "Execute show commands (deprecated, use 'any')";
      tailf:actionpoint ncsinternal {
        tailf:internal;
      }
      input {
        leaf-list args {
          tailf:cli-drop-node-name;
          tailf:cli-flat-list-syntax;
          type string {
            tailf:info "show argument(s)";
          }
        }
      }
      output {
        leaf result {
          type string;
        }
      }
    }

    // clear [arg 1] .. [arg N]
    tailf:action clear {
      tailf:info "Reset functions (deprecated, use 'any')";
      tailf:actionpoint ncsinternal {
        tailf:internal;
      }
      input {
        leaf-list args {
          tailf:cli-drop-node-name;
          tailf:cli-flat-list-syntax;
          type string {
            tailf:info "clear argument(s)";
          }
        }
      }
      output {
        leaf result {
          type string;
        }
      }
    }

    // copy [arg 1] .. [arg N]
    tailf:action copy {
      tailf:info "Copy from one file to another (deprecated, use 'any')";
      tailf:actionpoint ncsinternal {
        tailf:internal;
      }
      input {
        leaf-list args {
          tailf:cli-drop-node-name;
          tailf:cli-flat-list-syntax;
          type string {
            tailf:info "copy argument(s)";
          }
        }
      }
      output {
        leaf result {
          type string;
        }
      }
    }

    // reload [arg 1] .. [arg N]
    tailf:action reload {
      tailf:info "Halt and perform a cold restart (deprecated, use 'any')";
      tailf:actionpoint ncsinternal {
        tailf:internal;
      }
      input {
        leaf-list args {
          tailf:cli-drop-node-name;
          tailf:cli-flat-list-syntax;
          type string {
            tailf:info "reload argument(s)";
          }
        }
      }
      output {
        leaf result {
          type string;
        }
      }
    }

    // crypto key
    tailf:action "crypto" {
      tailf:info "Encryption module (deprecated, use 'any')";
      tailf:actionpoint ncsinternal {
        tailf:internal;
      }
      input {
        leaf-list "key" {
          tailf:info "Long term key operations";
          tailf:cli-flat-list-syntax;
          type string {
            tailf:info "crypto key argument(s)";
          }
        }
      }
      output {
        leaf result {
          type string;
        }
      }
    }

  }
}


/// ========================================================================
//                          EOF
/// ========================================================================
