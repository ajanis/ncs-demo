module cisco-ios-cli-3.8 {
  yang-version 1.1;
  namespace "http://tail-f.com/ns/ned-id/cisco-ios-cli-3.8";
  prefix cisco-ios-cli-3.8;

  import cisco-ios-cli {
    prefix family;
  }

  identity cisco-ios-cli-3.8 {
    base family:cisco-ios-cli;
  }
}
