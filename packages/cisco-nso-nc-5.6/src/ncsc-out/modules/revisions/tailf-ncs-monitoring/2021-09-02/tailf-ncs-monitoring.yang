module tailf-ncs-monitoring {
  // Generated by yanger -t ncs
  tailf:mount-id "cisco-nso-nc-5.6:cisco-nso-nc-5.6";
  tailf:ncs-device-type "netconf";

  namespace "http://tail-f.com/yang/ncs-monitoring";
  prefix tfnm;

  import tailf-common-monitoring {
    prefix tfcg;
    revision-date 2021-09-02;
  }
  import tailf-common {
    prefix tailf;
  }
  import tailf-ncs-internal-mount {
    prefix ncs;
  }

  organization
    "Tail-f Systems";
  description
    "This module defines status objects for monitoring of NCS.

     Copyright 2011-2021 Cisco Systems, Inc.
     All rights reserved.
     Permission is hereby granted to redistribute this file without
     modification.";

  revision 2021-09-02 {
    description
      "Released as part of NCS-5.6.

       Imported latest tailf-common-monitoring module.";
  }
  revision 2019-04-09 {
    description
      "Released as part of NCS-5.1.

       Imported latest tailf-common-monitoring module.";
  }
  revision 2018-06-14 {
    description
      "Released as part of NCS-4.7.

       Imported latest tailf-common-monitoring module.";
  }
  revision 2015-11-24 {
    description
      "Released as a part of NCS-4.1.

       Added /ncs-state/patches/patches-directory.";
  }
  revision 2015-06-16 {
    description
      "Released as a part of NCS-4.0.

       Removed deprecated candidate db-mode.";
  }
  revision 2014-11-19 {
    description
      "Released as part of NCS-3.3.

       Added /ncs-state/patches/loaded-module/compile-time.";
  }
  revision 2014-02-20 {
    description
      "Released as part of NCS-3.0.2.

       Added /ncs-state/patches.";
  }
  revision 2013-06-14 {
    description
      "Released as part of NCS-2.3.

       Imported latest tailf-common-monitoring module.

       Added 'servicepoint' list for NCS servicepoints.";
  }
  revision 2013-03-07 {
    description
      "Released as part of NCS-2.2.

       Imported latest tailf-common-monitoring module.";
  }
  revision 2012-11-08 {
    description
      "Released as part of NCS-2.1.

       Imported latest tailf-common-monitoring module.";
  }
  revision 2012-03-08 {
    description
      "Released as part of NCS-1.9.

       Imported latest tailf-common-monitoring module.";
  }
  revision 2011-12-08 {
    description
      "Released as part of NCS-1.8.

       Imported latest tailf-common-monitoring module.";
  }
  revision 2011-09-22 {
    description
      "Released as part of NCS-1.7.";
  }

  augment "/ncs:devices/ncs:device/ncs:config" {
    // NCS drop config false container 'ncs-state'
  }
  augment "/ncs:devices/ncs:device/ncs:live-status" {
    container ncs-state {
      tailf:ncs-device-type "netconf";
      tailf:display-when "not(../../ncs:module) or ../../ncs:module[ncs:name='tailf-ncs-monitoring'] or (../../ncs:live-status-protocol[not(ncs:capability)]) or (../../ncs:live-status-protocol/ncs:capability/ncs:module[.='tailf-ncs-monitoring'])";
      container patches {
        tailf:action load-modules {
          tailf:actionpoint ncsproxy {
            tailf:internal;
          }
          description
            "Loads a set of modules from the patches directory or
             from the NCS installation.

             The patches directory is ${NCS_DIR}/lib/ncs/patches.  If
             NCS is installed as a system installation, this is
             by default /opt/ncs/current/lib/ncs/patches.  The leaf
             'patches-directory' contains the path to this directory.

             If a module is present in the patches directory, it is
             loaded from this directory.  If it is not present in
             the patches directory, it is loaded from the NCS installation.

             Thus, in order to load a patch, drop the module in the patches
             directory and execute 'load-modules'.  In order to unload the
             patch, remove the file and execute 'load-modules'.

             If NCS restarts, it will load all modules present in the
             patches directory before loading from the NCS installation.";
          // NCS drop tailf:actionpoint
          input {
            leaf-list name {
              type string;
              min-elements 1;
              description
                "The name of a module to load.";
            }
            leaf force-purge {
              type empty;
              description
                "By default, NCS uses code:soft_purge() before loading the
                 new module.  If code:soft_purge() fails, the action
                 fails.  If 'force-purge' is given, code:purge() is used.";
            }
          }
        }
        leaf patches-directory {
          type string;
          description
            "The path to the directory from which patches are loaded.";
        }
        list loaded-module {
          description
            "List of patches loaded into the system.";
          key "name";
          leaf name {
            type string;
          }
          leaf version {
            type string;
          }
          leaf compile-time {
            type string;
          }
        }
      }
      uses tfcg:live_ncs_common-monitoring-objects {
        augment "internal/callpoints" {
          list servicepoint {
            key "id";
            uses tfcg:live_ncs_callpoint-entry;
          }
        }
      }
    }
  }
  augment "/ncs:devices/ncs:template/ncs:ned-id/ncs:config" {
    // NCS drop config false container 'ncs-state'
  }
}
