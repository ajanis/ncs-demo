module cisco-nso-nc-5.6 {
  yang-version 1.1;
  namespace "http://tail-f.com/ns/ned-id/cisco-nso-nc-5.6";
  prefix cisco-nso-nc-5.6;

  import cisco-nso-nc {
    prefix family;
  }

  identity cisco-nso-nc-5.6 {
    base family:cisco-nso-nc;
  }
}
