module a10-acos-cli-3.0 {
  yang-version 1.1;
  namespace "http://tail-f.com/ns/ned-id/a10-acos-cli-3.0";
  prefix a10-acos-cli-3.0;

  import a10-acos-cli {
    prefix family;
  }

  identity a10-acos-cli-3.0 {
    base family:a10-acos-cli;
  }
}
