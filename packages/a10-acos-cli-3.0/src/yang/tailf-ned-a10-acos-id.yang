module tailf-ned-a10-acos-id {
  namespace 'http://tail-f.com/ned/a10-acos-id';
  prefix a10-acos-id;

  import tailf-ncs-ned {
    prefix ned;
  }

  identity a10-acos {
    base ned:cli-ned-id;
  }
}
