module tailf-ned-cisco-ios-stats {
  // Generated by yanger -t ncs
  tailf:mount-id "cisco-ios-cli-3.0:cisco-ios-cli-3.0";
  tailf:ncs-device-type "cli-ned";

  namespace "urn:ios-stats";
  prefix ios-stats;

  import tailf-common {
    prefix tailf;
  }
  import tailf-ncs {
    prefix ncs;
  }

  typedef ncs_rpc_notif_ipv4-prefix {
    type string {
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
  }

  typedef ncs_rpc_notif_ipv6-prefix {
    type string {
      pattern '((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(/(([0-9])|([0-9]{2})|(1[0-1][0-9])|(12[0-8])))';
      pattern '(([^:]+:){6}(([^:]+:[^:]+)|(.*\..*)))|((([^:]+:)*[^:]+)?::(([^:]+:)*[^:]+)?)(/.+)';
    }
  }

  typedef live_ncs_ipv4-prefix {
    type string {
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
  }

  typedef live_ncs_ipv6-prefix {
    type string {
      pattern '((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(/(([0-9])|([0-9]{2})|(1[0-1][0-9])|(12[0-8])))';
      pattern '(([^:]+:){6}(([^:]+:[^:]+)|(.*\..*)))|((([^:]+:)*[^:]+)?::(([^:]+:)*[^:]+)?)(/.+)';
    }
  }

  typedef ipv4-prefix {
    type string {
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
  }

  typedef ipv6-prefix {
    type string {
      pattern '((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(/(([0-9])|([0-9]{2})|(1[0-1][0-9])|(12[0-8])))';
      pattern '(([^:]+:){6}(([^:]+:[^:]+)|(.*\..*)))|((([^:]+:)*[^:]+)?::(([^:]+:)*[^:]+)?)(/.+)';
    }
  }

  augment "/ncs:devices/ncs:device/ncs:rpc" {
    container rpc-idle-timeout {
      tailf:ncs-device-type "cli-ned";
      tailf:display-when "not(../../ncs:module) or ../../ncs:module[ncs:name='tailf-ned-cisco-ios-stats']";
      tailf:action idle-timeout {
        tailf:actionpoint ncsproxy {
          tailf:internal;
        }
        // NCS drop tailf:actionpoint
        input {
          leaf time {
            type int32;
          }
        }
        output {
          leaf result {
            type string;
          }
        }
      }
    }
  }
  augment "/ncs:devices/ncs:device-group/ncs:ned-id/ncs:rpc" {
    container rpc-idle-timeout {
      tailf:ncs-device-type "cli-ned";
      tailf:display-when "/ncs:devices/ncs:device[ncs:name=current()/../../../ncs:member]/ncs:module[ncs:name='tailf-ned-cisco-ios-stats']";
      tailf:action idle-timeout {
        tailf:actionpoint ncsproxy {
          tailf:internal;
        }
        // NCS drop tailf:actionpoint
        input {
          leaf time {
            type int32;
          }
        }
        output {
          container "device" {
            leaf "name" {
              type string;
            }
            leaf "info" {
              type string;
            }
            container "result" {
              leaf result {
                type string;
              }
            }
          }
        }
      }
    }
  }
  augment "/ncs:devices/ncs:device/ncs:config" {
    container commands {
      tailf:ncs-device-type "cli-ned";
      tailf:display-when "not(../../ncs:module) or ../../ncs:module[ncs:name='tailf-ned-cisco-ios-stats']";
      tailf:action idle-timeout {
        tailf:actionpoint ncsproxy {
          tailf:internal;
        }
        // NCS drop tailf:actionpoint
        input {
          leaf time {
            type int32;
          }
        }
        output {
          leaf result {
            type string;
          }
        }
      }
      tailf:action version {
        tailf:actionpoint ncsproxy {
          tailf:internal;
        }
        // NCS drop tailf:actionpoint
        input;
        output {
          leaf result {
            type string;
          }
        }
      }
    }
    // NCS drop config false list interfaces
  }
  augment "/ncs:devices/ncs:device/ncs:live-status" {
    container commands {
      tailf:ncs-device-type "cli-ned";
      tailf:display-when "not(../../ncs:module) or ../../ncs:module[ncs:name='tailf-ned-cisco-ios-stats'] or (../../ncs:live-status-protocol[not(ncs:capability)]) or (../../ncs:live-status-protocol/ncs:capability/ncs:module[.='tailf-ned-cisco-ios-stats'])";
      tailf:action idle-timeout {
        tailf:actionpoint ncsproxy {
          tailf:internal;
        }
        // NCS drop tailf:actionpoint
        input {
          leaf time {
            type int32;
          }
        }
        output {
          leaf result {
            type string;
          }
        }
      }
      tailf:action version {
        tailf:actionpoint ncsproxy {
          tailf:internal;
        }
        // NCS drop tailf:actionpoint
        input;
        output {
          leaf result {
            type string;
          }
        }
      }
    }
    list interfaces {
      tailf:ncs-device-type "cli-ned";
      tailf:display-when "not(../ncs:module) or ../ncs:module[ncs:name='tailf-ned-cisco-ios-stats'] or (../ncs:live-status-protocol[not(ncs:capability)]) or (../ncs:live-status-protocol/ncs:capability/ncs:module[.='tailf-ned-cisco-ios-stats'])";
      key "type name";
      leaf name {
        type string;
      }
      leaf type {
        type string;
      }
      leaf ip-address {
        type union {
          type live_ncs_ipv4-prefix;
          type live_ncs_ipv6-prefix;
        }
      }
      leaf mac-address {
        type string;
      }
    }
  }
}
