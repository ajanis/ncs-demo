module cisco-ios-cli-3.0 {
  yang-version 1.1;
  namespace "http://tail-f.com/ns/ned-id/cisco-ios-cli-3.0";
  prefix cisco-ios-cli-3.0;

  import cisco-ios-cli {
    prefix family;
  }

  identity cisco-ios-cli-3.0 {
    base family:cisco-ios-cli;
  }
}
