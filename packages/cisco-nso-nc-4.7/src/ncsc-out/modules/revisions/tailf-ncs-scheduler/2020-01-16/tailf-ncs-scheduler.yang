module tailf-ncs-scheduler {
  // Generated by yanger -t ncs
  tailf:mount-id "cisco-nso-nc-4.7:cisco-nso-nc-4.7";
  tailf:ncs-device-type "netconf";

  namespace "http://tail-f.com/ns/ncs-scheduler";
  prefix scheduler;

  import ietf-yang-types {
    prefix yang;
  }
  import tailf-common {
    prefix tailf;
  }
  import tailf-ncs-internal-mount {
    prefix ncs;
  }

  organization
    "Tail-f Systems";
  description
    "This module contains a collection of YANG definitions for
     configuring scheduled tasks in NCS.";

  revision 2020-01-16 {
    description
      "Released as part of NCS-4.7.6.

       Added sequence-no leaf as part of key to
       /scheduler/task/history.";
  }
  revision 2018-06-21 {
    description
      "Released as part of NCS-4.7.

       Added /scheduler/task/enabled.

       The type of /scheduler/task/action-name changed from
       yang:yang-identifier to tailf:identifier-ref.

       Added /scheduler/task/history/result.";
  }
  revision 2017-11-30 {
    description
      "Released as part of NCS-4.5.2.

       Added /scheduler/task/ha-mode.
       Added /scheduler/task/ha-node-id.

       Added /scheduler/task/time.
       Added /scheduler/task/keep.

       The type of /scheduler/task/history/duration changed from
       string to decimal64.";
  }
  revision 2017-09-28 {
    description
      "Released as part of NCS-4.5.

       Initial revision.";
  }

  augment "/ncs:devices/ncs:device/ncs:config" {
    container scheduler {
      tailf:ncs-device-type "netconf";
      tailf:display-when "not(../../ncs:module) or ../../ncs:module[ncs:name='tailf-ncs-scheduler']";
      description
        "Time-based job scheduler suitable for scheduling periodic
         background work.";
      tailf:action suspend {
        tailf:actionpoint ncsproxy {
          tailf:internal;
        }
        tailf:display-when "../suspended = 'false'" {
          tailf:xpath-root 3;
        }
        description
          "Suspend all tasks in the scheduler.";
        // NCS drop tailf:actionpoint
      }
      tailf:action resume {
        tailf:actionpoint ncsproxy {
          tailf:internal;
        }
        tailf:display-when "../suspended = 'true'" {
          tailf:xpath-root 3;
        }
        description
          "Resume all tasks in the scheduler.";
        // NCS drop tailf:actionpoint
      }
      // NCS drop config false leaf suspended
      list task {
        tailf:info
          "The list of configured tasks.";
        description
          "Examples:

             Run sync-from on all devices 2 AM on the 1st every month:

               name: sync
               schedule: 0 2 1 * *
               action-name: sync-from
               action-node: /devices

             Purge the completed queue-item list 4:30 AM every Sunday:

               name: purge
               schedule: 30 4 * * 0
               action-name: purge
               action-node: /devices/commit-queue/completed";
        key "name";
        leaf name {
          type string;
          description
            "A unique name for this task.";
        }
        // NCS drop tailf:callpoint
        choice trigger {
          mandatory true;
          case schedule {
            leaf schedule {
              description
                "Standard Vixie Cron expression to represent the
                 periodicity in which the task should run.

                 ---------- minute (0 - 59)
                 | ---------- hour (0 - 23)
                 | | ---------- day of month (1 - 31)
                 | | | ---------- month (1 - 12)
                 | | | | ---------- day of week (0 - 6) (Sunday to Saturday)
                 | | | | |
                 * * * * *";
              type string;
              // NCS drop tailf:validate
            }
          }
          case time {
            leaf time {
              must "../ha-mode = 'master'" {
                tailf:xpath-root 3;
                error-message "Time based tasks can only be configured to run on the HA master node.";
              }
              tailf:display-when "../ha-mode = 'master'" {
                tailf:xpath-root 3;
              }
              description
                "A particular time when the task should run.

                 The task will be triggered at the second.
                 Fractions of the second and time zone will be ignored.";
              type yang:date-and-time;
              mandatory true;
            }
            leaf keep {
              description
                "Keep configured task after it has finished successfully.";
              type empty;
            }
          }
        }
        leaf action-node {
          description
            "When the task is triggered, the 'action-name' action is invoked
             on the 'action-node' instance. The action is run as the user
             that configured the task.

             If the 'action-node' is given as an XPath 1.0 expression, the
             expression is evaluated with the root as the context node,
             and the expression must return a node set. The 'action-name'
             action is invoked on the nodes in this node set.";
          type union {
            // NCS patched to string, due to LSA partial NED
            type string;
            type yang:xpath1.0;
          }
          mandatory true;
          // NCS drop tailf:validate
        }
        leaf action-name {
          description
            "The action to be invoked. Can be given either as just the name
             of the action without a prefix, or the name of the action
             prefixed with the prefix defined in the YANG module where the
             action is defined. The prefix is required if more than one
             action with the given name is present due to augmentations.";
          type tailf:identifier-ref;
          mandatory true;
        }
        leaf action-params {
          description
            "Action parameters in XML format.";
          type string;
        }
        leaf ha-mode {
          description
            "The HA mode in which the task will run.

             The setting will not have any effect if HA isn't configured.";
          type enumeration {
            enum "master";
            enum "slave";
          }
          default "master";
        }
        leaf ha-node-id {
          when "../ha-mode = 'slave'" {
            tailf:xpath-root 3;
          }
          type string;
          description
            "The HA cluster node on which the task is allowed to run.";
        }
        leaf enabled {
          description
            "Whether the task is enabled or not.";
          type boolean;
          default "true";
        }
        // NCS drop fully hidden leaf 'local-user'
        // NCS drop config false leaf 'is-running'
        // NCS drop config false list history
        tailf:action get-next-run-times {
          tailf:actionpoint ncsproxy {
            tailf:internal;
          }
          description
            "Display the next run times for the task.";
          // NCS drop tailf:actionpoint
          input {
            leaf display {
              type uint16 {
                range "1..100";
              }
              default "5";
            }
          }
          output {
            leaf-list next-run-time {
              type string;
            }
          }
        }
      }
    }
  }
  augment "/ncs:devices/ncs:device/ncs:live-status" {
    container scheduler {
      tailf:ncs-device-type "netconf";
      tailf:display-when "not(../../ncs:module) or ../../ncs:module[ncs:name='tailf-ncs-scheduler'] or (../../ncs:live-status-protocol[not(ncs:capability)]) or (../../ncs:live-status-protocol/ncs:capability/ncs:module[.='tailf-ncs-scheduler'])";
      description
        "Time-based job scheduler suitable for scheduling periodic
         background work.";
      tailf:action suspend {
        tailf:actionpoint ncsproxy {
          tailf:internal;
        }
        tailf:display-when "../suspended = 'false'" {
          tailf:xpath-root 3;
        }
        description
          "Suspend all tasks in the scheduler.";
        // NCS drop tailf:actionpoint
      }
      tailf:action resume {
        tailf:actionpoint ncsproxy {
          tailf:internal;
        }
        tailf:display-when "../suspended = 'true'" {
          tailf:xpath-root 3;
        }
        description
          "Resume all tasks in the scheduler.";
        // NCS drop tailf:actionpoint
      }
      leaf suspended {
        description
          "Whether the scheduler is suspended or not.";
        type boolean;
        // NCS drop default statement
        // NCS drop tailf:cdb-oper
      }
      list task {
        tailf:info
          "The list of configured tasks.";
        description
          "Examples:

             Run sync-from on all devices 2 AM on the 1st every month:

               name: sync
               schedule: 0 2 1 * *
               action-name: sync-from
               action-node: /devices

             Purge the completed queue-item list 4:30 AM every Sunday:

               name: purge
               schedule: 30 4 * * 0
               action-name: purge
               action-node: /devices/commit-queue/completed";
        key "name";
        leaf name {
          type string;
          description
            "A unique name for this task.";
        }
        // NCS drop tailf:callpoint
        choice trigger {
          // NCS drop mandatory statement
          case schedule {
            leaf schedule {
              description
                "Standard Vixie Cron expression to represent the
                 periodicity in which the task should run.

                 ---------- minute (0 - 59)
                 | ---------- hour (0 - 23)
                 | | ---------- day of month (1 - 31)
                 | | | ---------- month (1 - 12)
                 | | | | ---------- day of week (0 - 6) (Sunday to Saturday)
                 | | | | |
                 * * * * *";
              type string;
              // NCS drop tailf:validate
            }
          }
          case time {
            leaf time {
              // NCS drop must statement
              // NCS drop tailf-common:display-when statement
              description
                "A particular time when the task should run.

                 The task will be triggered at the second.
                 Fractions of the second and time zone will be ignored.";
              type yang:date-and-time;
              // NCS drop mandatory statement
            }
            leaf keep {
              description
                "Keep configured task after it has finished successfully.";
              type empty;
            }
          }
        }
        leaf action-node {
          description
            "When the task is triggered, the 'action-name' action is invoked
             on the 'action-node' instance. The action is run as the user
             that configured the task.

             If the 'action-node' is given as an XPath 1.0 expression, the
             expression is evaluated with the root as the context node,
             and the expression must return a node set. The 'action-name'
             action is invoked on the nodes in this node set.";
          type union {
            // NCS patched to string, due to LSA partial NED
            type string;
            type yang:xpath1.0;
          }
          // NCS drop mandatory statement
          // NCS drop tailf:validate
        }
        leaf action-name {
          description
            "The action to be invoked. Can be given either as just the name
             of the action without a prefix, or the name of the action
             prefixed with the prefix defined in the YANG module where the
             action is defined. The prefix is required if more than one
             action with the given name is present due to augmentations.";
          type tailf:identifier-ref;
          // NCS drop mandatory statement
        }
        leaf action-params {
          description
            "Action parameters in XML format.";
          type string;
        }
        leaf ha-mode {
          description
            "The HA mode in which the task will run.

             The setting will not have any effect if HA isn't configured.";
          type enumeration {
            enum "master";
            enum "slave";
          }
          // NCS drop default statement
        }
        leaf ha-node-id {
          // NCS drop when statement
          type string;
          description
            "The HA cluster node on which the task is allowed to run.";
        }
        leaf enabled {
          description
            "Whether the task is enabled or not.";
          type boolean;
          // NCS drop default statement
        }
        // NCS drop fully hidden leaf 'local-user'
        leaf is-running {
          description
            "Whether the task is currently executing.";
          type boolean;
          // NCS drop default statement
          // NCS drop tailf:cdb-oper
        }
        list history {
          description
            "History of last five runs.";
          key "when sequence-no";
          // NCS drop tailf:cdb-oper
          leaf when {
            type yang:date-and-time;
            description
              "When the task was started.";
          }
          leaf sequence-no {
            type uint8;
          }
          leaf duration {
            type decimal64 {
              fraction-digits 3;
            }
            units "seconds";
            description
              "Duration of the task in seconds.";
          }
          leaf succeeded {
            type boolean;
            description
              "Whether the task succeeded or failed.";
          }
          anyxml result {
            description
              "Possible output from the action in XML format.";
          }
          leaf info {
            type string;
            description
              "Possible error message in case the task was not successful.";
          }
        }
        tailf:action get-next-run-times {
          tailf:actionpoint ncsproxy {
            tailf:internal;
          }
          description
            "Display the next run times for the task.";
          // NCS drop tailf:actionpoint
          input {
            leaf display {
              type uint16 {
                range "1..100";
              }
              default "5";
            }
          }
          output {
            leaf-list next-run-time {
              type string;
            }
          }
        }
      }
    }
  }
}
