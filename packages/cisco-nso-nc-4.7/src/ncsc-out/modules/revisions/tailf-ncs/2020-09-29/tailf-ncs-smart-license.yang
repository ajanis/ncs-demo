submodule tailf-ncs-smart-license {
  // Generated by yanger -t ncs
  tailf:mount-id "cisco-nso-nc-4.7:cisco-nso-nc-4.7";

  belongs-to tailf-ncs {
    prefix ncs;
  }

  import tailf-common {
    prefix tailf;
  }
  import ietf-inet-types {
    prefix inet;
  }
  include tailf-ncs-common;
  import tailf-ncs-internal-mount {
    prefix ncs-internal;
  }

  organization
    "Tail-f Systems";
  description
    "This submodule contains a collection of YANG definitions for
     configuring and monitoring the Smart Licensing Java Virtual Machine
     in NCS.";

  revision 2018-03-01 {
    description
      "Released as part of NCS-4.6.

       Updated description of /smart-license/smart-agent/production-url,
       /smart-license/smart-agent/alpha-url, and
       /smart-license/smart-agent/override-url.";
  }
  revision 2017-09-28 {
    description
      "Released as part of NCS-4.5.

       Updated default url for 'alpha-url'.";
  }
  revision 2017-07-09 {
    description
      "Released as part of NCS-4.4.2.1.

       Updated description of /smart-license/smart-agent/java-executable,
       /smart-license/smart-agent/java-options, and
       /smart-license/smart-agent/proxy/url.";
  }
  revision 2017-03-16 {
    description
      "Released as part of NCS-4.4.

       Added smart-license/smart-agent/proxy";
  }
  revision 2016-11-24 {
    description
      "Released as part of NCS-4.3.

       Changed default value for alpha server URL.";
  }
  revision 2016-05-26 {
    description
      "Released as part of NCS-4.2.";
  }

  augment "/ncs-internal:devices/ncs-internal:device/ncs-internal:config" {
    container smart-license {
      tailf:ncs-device-type "netconf";
      tailf:display-when "not(../../ncs-internal:module) or ../../ncs-internal:module[ncs-internal:name='tailf-ncs']";
      leaf development-mode {
        tailf:info
          "Is NSO smart licensing in development mode?";
        type boolean;
        default "false";
        description
          "If set to true, smart agent development licenses are
           used. Otherwise production licenses are assumed.";
      }
      container smart-agent {
        tailf:info
          "Control of the NCS Smart Licensing Java VM";
        description
          "Configuration parameters to control how NCS shall start
           (and restart) the Smart Licensing Java Virtual Machine,
           configuration parameters to control various properties,
           e.g. logging and statistics data about the Java Smart
           Licensing code.";
        leaf java-executable {
          tailf:info
            "Smart licensing Java VM executable";
          type string;
          default "java";
          description
            "The Java VM executable that NCS will use for smart licensing.

             NOTE: If a value is set for
             /ncs-config/smart-license/smart-agent/java-executable in
             ncs.conf, the value set here is ignored.";
        }
        leaf java-options {
          tailf:info
            "Smart licensing Java VM start options";
          type string;
          default "-Xmx64M -Xms16M -Djava.security.egd=file:/dev/./urandom";
          description
            "Options which NCS will use when starting the Java VM.

             NOTE: If a value is set for
             /ncs-config/smart-license/smart-agent/java-options in
             ncs.conf, the value set here is ignored.";
        }
        leaf enabled {
          tailf:hidden "smart-licensing";
          type boolean;
          default "false";
        }
        leaf production-mode {
          tailf:hidden "smart-licensing";
          tailf:info
            "Used to run in production mode or for when testing
             with the alpha account.";
          type boolean;
          default "true";
          description
            "For running in production or for when testing with the
             alpha account.";
        }
        leaf production-url {
          tailf:hidden "smart-licensing";
          tailf:info
            "Smart licensing agent production backend URL
               (https or http scheme)";
          type inet:uri {
            pattern 'https?://.*';
          }
          default "https://tools.cisco.com/its/service/oddce/services/DDCEService";
          description
            "The 'base' production URL for the smart licensing agent.

             NOTE: If a value is set for
             /ncs-config/smart-license/smart-agent/production-url in
             ncs.conf, the value set here is ignored.";
        }
        leaf alpha-url {
          tailf:hidden "smart-licensing";
          tailf:info
            "Smart licensing agent alpha backend URL (https or http scheme)";
          type inet:uri {
            pattern 'https?://.*';
          }
          default "https://pteodc-alphastg.cloudapps.cisco.com/its/service/oddce/services/DDCEService";
          description
            "The 'base' alpha URL for the smart licensing agent.

             NOTE: If a value is set for
             /ncs-config/smart-license/smart-agent/alpha-url in
             ncs.conf, the value set here is ignored.";
        }
        container override-url {
          tailf:info
            "Used to force an overriding smart licensing backend URL.";
          presence "use URL that overrides smart licensing backend URL.";
          leaf url {
            tailf:info
              "Smart licensing agent backend URL (https or http scheme)";
            type inet:uri {
              pattern 'https?://.*';
            }
            description
              "The 'base' URL for the smart agent, which can be used
               to point at a satellite in a smart agent satellite configuration.

               NOTE: If a value is set for
               /ncs-config/smart-license/smart-agent/override-url in
               ncs.conf, the value set here is ignored.";
          }
        }
        container stdout-capture {
          tailf:info
            "Capture stdout and stderr";
          description
            "Capture stdout and stderr from the Smart Licensing Java VM.";
          leaf enabled {
            tailf:info
              "Enable stdout and stderr capture";
            type boolean;
            default "false";
          }
          leaf file {
            tailf:info
              "Write Smart Licensing Java VM output to file";
            type string;
            default "./ncs-smart-licensing.log";
            description
              "Write Smart Licensing Java VM output to filename.";
          }
          leaf stdout {
            tailf:info
              "Write output to stdout";
            type empty;
            description
              "If present write output to stdout, useful together
               with the --foreground flag to ncs.";
          }
        }
        container proxy {
          tailf:info
            "Used to configure a proxy URL.";
          presence "use proxy URL for smart licensing.";
          leaf url {
            tailf:info
              "Smart licensing agent proxy URL (https or http scheme)";
            type inet:uri {
              pattern 'https?://.*:\d+';
            }
            description
              "Proxy URL for the smart licensing agent containing both
               host/address and port.

               NOTE: If a value is set for
               /ncs-config/smart-license/smart-agent/proxy/url in
               ncs.conf, the value set here is ignored.";
          }
        }
        // NCS drop config false leaf 'start-status'
        tailf:action restart {
          tailf:actionpoint ncsproxy {
            tailf:internal;
          }
          tailf:info
            "Restart the Smart Licensing Java VM";
          description
            "Restart the Smart Licensning Java VM.";
          // NCS drop tailf:actionpoint
          output {
            leaf result {
              type string;
            }
          }
        }
      }
      tailf:action register {
        tailf:actionpoint ncsproxy {
          tailf:internal;
        }
        // NCS drop tailf:actionpoint
        tailf:info
          "Register device for Smart Licensing";
        input {
          leaf idtoken {
            mandatory true;
            tailf:info
              "User Registration Token to register device";
            type string;
          }
          leaf force {
            tailf:info
              "Override existing registration information";
            type boolean;
            default "false";
          }
        }
        output {
          leaf result {
            type string;
          }
        }
      }
      tailf:action deregister {
        tailf:actionpoint ncsproxy {
          tailf:internal;
        }
        tailf:info
          "Deregister device from Smart Licensing";
        // NCS drop tailf:actionpoint
        output {
          leaf result {
            type string;
          }
        }
      }
      tailf:action renew {
        tailf:actionpoint ncsproxy {
          tailf:internal;
        }
        tailf:info
          "Manually renew Smart Licensing";
        // NCS drop tailf:actionpoint
        input {
          choice what {
            mandatory true;
            case what-id {
              leaf id {
                tailf:info
                  "Renew registration with Smart Licensing [default]";
                type empty;
              }
            }
            case what-auth {
              leaf auth {
                tailf:info
                  "Renew authorization of Smart Licenses in use";
                type empty;
              }
            }
          }
        }
        output {
          leaf result {
            type string;
          }
        }
      }
      tailf:action show {
        tailf:actionpoint ncsproxy {
          tailf:internal;
        }
        tailf:info
          "Show Smart Licensing state information";
        // NCS drop tailf:actionpoint
        input {
          choice what {
            case show-status {
              leaf status {
                type empty;
                tailf:info
                  "Show overall Smart Licensing status [default]";
              }
            }
            case show-summary {
              leaf summary {
                type empty;
                tailf:info
                  "Show Smart Licensing status summary";
              }
            }
            case show-udi {
              leaf UDI {
                type empty;
                tailf:info
                  "Show the device UDI";
              }
            }
            case show-usage {
              leaf usage {
                type empty;
                tailf:info
                  "Show Smart Licensing license usage";
              }
            }
            case show-all {
              leaf all {
                type empty;
                tailf:info
                  "Show all Smart Licensing information";
              }
            }
            case show-tech-support {
              leaf tech-support {
                type empty;
                tailf:info
                  "Show Smart Licensing tech support information";
              }
            }
            case show-trace {
              leaf trace {
                type empty;
                tailf:info
                  "Show Smart Licensing trace status";
              }
            }
          }
        }
        output {
          leaf result {
            type string;
          }
        }
      }
      // NCS drop config false list entitlements
    }
  }
  augment "/ncs-internal:devices/ncs-internal:device/ncs-internal:live-status" {
    container smart-license {
      tailf:ncs-device-type "netconf";
      tailf:display-when "not(../../ncs-internal:module) or ../../ncs-internal:module[ncs-internal:name='tailf-ncs'] or (../../ncs-internal:live-status-protocol[not(ncs-internal:capability)]) or (../../ncs-internal:live-status-protocol/ncs-internal:capability/ncs-internal:module[.='tailf-ncs'])";
      leaf development-mode {
        tailf:info
          "Is NSO smart licensing in development mode?";
        type boolean;
        // NCS drop default statement
        description
          "If set to true, smart agent development licenses are
           used. Otherwise production licenses are assumed.";
      }
      container smart-agent {
        tailf:info
          "Control of the NCS Smart Licensing Java VM";
        description
          "Configuration parameters to control how NCS shall start
           (and restart) the Smart Licensing Java Virtual Machine,
           configuration parameters to control various properties,
           e.g. logging and statistics data about the Java Smart
           Licensing code.";
        leaf java-executable {
          tailf:info
            "Smart licensing Java VM executable";
          type string;
          // NCS drop default statement
          description
            "The Java VM executable that NCS will use for smart licensing.

             NOTE: If a value is set for
             /ncs-config/smart-license/smart-agent/java-executable in
             ncs.conf, the value set here is ignored.";
        }
        leaf java-options {
          tailf:info
            "Smart licensing Java VM start options";
          type string;
          // NCS drop default statement
          description
            "Options which NCS will use when starting the Java VM.

             NOTE: If a value is set for
             /ncs-config/smart-license/smart-agent/java-options in
             ncs.conf, the value set here is ignored.";
        }
        leaf enabled {
          tailf:hidden "smart-licensing";
          type boolean;
          // NCS drop default statement
        }
        leaf production-mode {
          tailf:hidden "smart-licensing";
          tailf:info
            "Used to run in production mode or for when testing
             with the alpha account.";
          type boolean;
          // NCS drop default statement
          description
            "For running in production or for when testing with the
             alpha account.";
        }
        leaf production-url {
          tailf:hidden "smart-licensing";
          tailf:info
            "Smart licensing agent production backend URL
               (https or http scheme)";
          type inet:uri {
            pattern 'https?://.*';
          }
          // NCS drop default statement
          description
            "The 'base' production URL for the smart licensing agent.

             NOTE: If a value is set for
             /ncs-config/smart-license/smart-agent/production-url in
             ncs.conf, the value set here is ignored.";
        }
        leaf alpha-url {
          tailf:hidden "smart-licensing";
          tailf:info
            "Smart licensing agent alpha backend URL (https or http scheme)";
          type inet:uri {
            pattern 'https?://.*';
          }
          // NCS drop default statement
          description
            "The 'base' alpha URL for the smart licensing agent.

             NOTE: If a value is set for
             /ncs-config/smart-license/smart-agent/alpha-url in
             ncs.conf, the value set here is ignored.";
        }
        container override-url {
          tailf:info
            "Used to force an overriding smart licensing backend URL.";
          presence "use URL that overrides smart licensing backend URL.";
          leaf url {
            tailf:info
              "Smart licensing agent backend URL (https or http scheme)";
            type inet:uri {
              pattern 'https?://.*';
            }
            description
              "The 'base' URL for the smart agent, which can be used
               to point at a satellite in a smart agent satellite configuration.

               NOTE: If a value is set for
               /ncs-config/smart-license/smart-agent/override-url in
               ncs.conf, the value set here is ignored.";
          }
        }
        container stdout-capture {
          tailf:info
            "Capture stdout and stderr";
          description
            "Capture stdout and stderr from the Smart Licensing Java VM.";
          leaf enabled {
            tailf:info
              "Enable stdout and stderr capture";
            type boolean;
            // NCS drop default statement
          }
          leaf file {
            tailf:info
              "Write Smart Licensing Java VM output to file";
            type string;
            // NCS drop default statement
            description
              "Write Smart Licensing Java VM output to filename.";
          }
          leaf stdout {
            tailf:info
              "Write output to stdout";
            type empty;
            description
              "If present write output to stdout, useful together
               with the --foreground flag to ncs.";
          }
        }
        container proxy {
          tailf:info
            "Used to configure a proxy URL.";
          presence "use proxy URL for smart licensing.";
          leaf url {
            tailf:info
              "Smart licensing agent proxy URL (https or http scheme)";
            type inet:uri {
              pattern 'https?://.*:\d+';
            }
            description
              "Proxy URL for the smart licensing agent containing both
               host/address and port.

               NOTE: If a value is set for
               /ncs-config/smart-license/smart-agent/proxy/url in
               ncs.conf, the value set here is ignored.";
          }
        }
        leaf start-status {
          tailf:info
            "";
          type enumeration {
            enum "stopped" {
              description
                "The Smart Licensing Java VM has been stopped or is not yet
                 started.";
              tailf:code-name "smart_licensing_stopped";
            }
            enum "started" {
              description
                "The Smart Licensing Java VM has been started.";
              tailf:code-name "smart_licensing_started";
            }
            enum "failed" {
              description
                "The Smart Licensing Java VM has terminated.
                 The Smart Licensing Java VM restart has been
                 disabled due to too many frequent restarts.";
              tailf:code-name "smart_licensing_failed";
            }
          }
          description
            "The status of the start of the Smart Licensning Java VM.";
          // NCS drop tailf:callpoint
        }
        tailf:action restart {
          tailf:actionpoint ncsproxy {
            tailf:internal;
          }
          tailf:info
            "Restart the Smart Licensing Java VM";
          description
            "Restart the Smart Licensning Java VM.";
          // NCS drop tailf:actionpoint
          output {
            leaf result {
              type string;
            }
          }
        }
      }
      tailf:action register {
        tailf:actionpoint ncsproxy {
          tailf:internal;
        }
        // NCS drop tailf:actionpoint
        tailf:info
          "Register device for Smart Licensing";
        input {
          leaf idtoken {
            mandatory true;
            tailf:info
              "User Registration Token to register device";
            type string;
          }
          leaf force {
            tailf:info
              "Override existing registration information";
            type boolean;
            default "false";
          }
        }
        output {
          leaf result {
            type string;
          }
        }
      }
      tailf:action deregister {
        tailf:actionpoint ncsproxy {
          tailf:internal;
        }
        tailf:info
          "Deregister device from Smart Licensing";
        // NCS drop tailf:actionpoint
        output {
          leaf result {
            type string;
          }
        }
      }
      tailf:action renew {
        tailf:actionpoint ncsproxy {
          tailf:internal;
        }
        tailf:info
          "Manually renew Smart Licensing";
        // NCS drop tailf:actionpoint
        input {
          choice what {
            mandatory true;
            case what-id {
              leaf id {
                tailf:info
                  "Renew registration with Smart Licensing [default]";
                type empty;
              }
            }
            case what-auth {
              leaf auth {
                tailf:info
                  "Renew authorization of Smart Licenses in use";
                type empty;
              }
            }
          }
        }
        output {
          leaf result {
            type string;
          }
        }
      }
      tailf:action show {
        tailf:actionpoint ncsproxy {
          tailf:internal;
        }
        tailf:info
          "Show Smart Licensing state information";
        // NCS drop tailf:actionpoint
        input {
          choice what {
            case show-status {
              leaf status {
                type empty;
                tailf:info
                  "Show overall Smart Licensing status [default]";
              }
            }
            case show-summary {
              leaf summary {
                type empty;
                tailf:info
                  "Show Smart Licensing status summary";
              }
            }
            case show-udi {
              leaf UDI {
                type empty;
                tailf:info
                  "Show the device UDI";
              }
            }
            case show-usage {
              leaf usage {
                type empty;
                tailf:info
                  "Show Smart Licensing license usage";
              }
            }
            case show-all {
              leaf all {
                type empty;
                tailf:info
                  "Show all Smart Licensing information";
              }
            }
            case show-tech-support {
              leaf tech-support {
                type empty;
                tailf:info
                  "Show Smart Licensing tech support information";
              }
            }
            case show-trace {
              leaf trace {
                type empty;
                tailf:info
                  "Show Smart Licensing trace status";
              }
            }
          }
        }
        output {
          leaf result {
            type string;
          }
        }
      }
      list entitlements {
        tailf:hidden "smart-licensing";
        // NCS drop tailf:display-groups
        tailf:info
          "list of current entitlements";
        // NCS drop tailf:callpoint
        key "entitlement";
        leaf entitlement {
          type string;
          description
            "Name of the device.";
        }
        leaf count {
          type uint32;
          description
            "count of entitlement";
        }
        leaf version {
          type string;
        }
      }
    }
  }
}
