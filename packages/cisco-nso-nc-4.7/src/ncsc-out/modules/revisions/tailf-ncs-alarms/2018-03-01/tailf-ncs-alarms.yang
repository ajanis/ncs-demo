module tailf-ncs-alarms {
  // Generated by yanger -t ncs
  tailf:mount-id "cisco-nso-nc-4.7:cisco-nso-nc-4.7";
  tailf:ncs-device-type "netconf";

  namespace "http://tail-f.com/ns/ncs-alarms";
  prefix al;

  import ietf-yang-types {
    prefix yang;
  }
  import tailf-ncs {
    prefix ncs;
  }
  import tailf-common {
    prefix tailf;
  }
  import tailf-ncs-internal-mount {
    prefix ncs-internal;
  }

  organization
    "Tail-f Systems";
  description
    "This module is an interface for managing alarms.  Main inputs to
     the module design are the 3GPP Alarm IRP and ITU-T X.733 alarm
     standards.  It describes an alarm list that represents the
     current alarms in the system. Cleared alarms stays in the list
     until deliberately removed.

     It is important to identify clearly what is to be considered the
     same alarm instance.  A unique alarm instance is the combination
     of device, managed object, alarm type, and optional specific problem.
     Alarm types are defined using YANG identities which allows for
     hierarchical alarm types. Specific problem is a string which allows
     for dynamic extension of the statically defined alarm types.
     In this way there is no ambiguity about how alarm and alarm clear
     correlation should be performed: the same device, managed object,
     alarm type, and specific problem shall be used.  The same is true
     for changing existing alarm states.  Severity and alarm text can
     be changed on an existing alarm.

     There is a clear separation between updates on the alarm
     from the underlying resource, like clear, and updates from
     an operator like acknowledge.

     Administrative actions like removing cleared alarms older
     than an age-spec is supported.";

  revision 2018-03-01 {
    description
      "Released as part of NCS-4.6.

       The status of dev-manager-internal-error identity changed from current
       to deprecated.

       The base identity for commit-through-queue-rollback-failed identity has
       been changed from alarm-type to ncs-dev-manager-alarm.";
  }
  revision 2017-06-14 {
    description
      "Release as part of NCS-4.4.2.

       Added commit-through-queue-rollback-error.";
  }
  revision 2017-03-16 {
    description
      "Released as part of NCS-4.4.

       Corrected description for grouping alarm-model-parameters.";
  }
  revision 2015-03-19 {
    description
      "Released as part of NCS-3.4.

       Added /alarms/control/notify-cli.";
  }
  revision 2014-12-09 {
    description
      "Released as part of NCS-3.3.0.1.

       Added service-activation-failure.";
  }
  revision 2014-11-19 {
    description
      "Released as part of NCS-3.3.

       Added abort-error.

       Updated descriptions of some alarms.";
  }
  revision 2014-06-30 {
    description
      "Released as part of NCS-3.2.

       Updated descriptions of the alarms.";
  }
  revision 2014-06-05 {
    description
      "Released as part of NCS-3.1.2.

       Added alarms package-load-failure and
       package-operation-failure identities.";
  }
  revision 2013-06-18 {
    description
      "Released as part of NCS-2.3.

       Added ncs-snmp-notification-receiver-alarm and
         receiver-configuration-error identities.";
  }
  revision 2013-04-24 {
    description
      "Released as part of NCS-2.2.1.

       Added missing-transaction-id identity.";
  }
  revision 2013-03-12 {
    description
      "Released as part of NCS-2.2.

       Added 'specific-problem-match' as a key in the
         /alarms/alarm-model/alarm-type list.

       Added new alarm-types related to commit-queue.";
  }
  revision 2012-08-30 {
    description
      "Released as part of NCS-2.0.

       Renamed 'alarm-list-container' to 'alarm-list' in /alarms.

       Renamed 'managed-device' to 'device' in the
         /alarms/alarm-list/alarm list.

       Added 'specific-problem' as a new key in the
         /alarms/alarm-list/alarm list.

       Expanded the type 'managed-object-t' to be a union of
         instance-identifier, object-identifier and string.

       Renamed the leaf-list 'any-object' to 'alt-managed-object'.

       Added the leaf-list 'alt-managed-object' to the
         /alarms/alarm-list/alarm list.

       Renamed 'when' to 'event-time' in the
         /alarms/alarm-list/alarm/status-change list.

       Added 'received-time' in the
         /alarms/alarm-list/alarm/status-change list and
         in the alarm-notification.

       Renamed 'alarm-type' to 'type' in the
         alarm-notification.

       Renamed 'severity' to 'perceived-severity' in the
         alarm-notification.

       Clarified the meaning of the leaf
         /alarms/alarm-list/alarm/last-status-change.

       Clarified the meaning of the leaf
         /alarms/alarm-list/alarm/status-change/when.

       Fixed the paths in the leafs in the
         /alarms/alarm-list/alarm/related-alarms list.

       Renamed 'alarm-handling-acknowledge' to 'handle-alarm' in the
         /alarms/alarm-list/alarm list.

       Added three groupings for common alarm parameters, alarm model
         parameters and alarm state change parameters.

       Added grouping for alarm summary counters.

       Added alarm summary per device and per device group.";
  }
  revision 2012-02-13 {
    description
      "Released as part of NCS-1.9.

       Modified /alarms/alarm-list-container/alarm/type to not be a
       leafref into alarm-model, since the corresponding entry might not
       exist.";
  }
  revision 2012-01-31 {
    description
      "Released as part of NCS-1.8.1.

       Modified the /alarms/alarm-model/has-clear leaf to also allow
       the value 'unknown'.";
  }
  revision 2011-09-27 {
    description
      "Released as part of NCS-1.7.";
  }
  revision 2011-05-28 {
    description
      "Released as part of NCS-1.6.";
  }
  revision 2011-03-01 {
    description
      "Released as part of NCS-1.5.";
  }
  revision 2010-12-07 {
    description
      "Released as part of NCS-1.4.2.

       Initial revision.";
  }

  typedef ncs_rpc_notif_managed-object-t {
    type union {
      // NCS patched to string, due to LSA partial NED
      type string;
      type yang:object-identifier;
      type string;
    }
    description
      "If the referenced managed object is modelled in YANG, this type
       will be an instance-identifier.  If the managed object is an SNMP
       object, the type will be an object-identifier.  If the managed
       object is anything else, for example a distinguished name or a CIM
       path, this type will be a string.";
  }

  typedef ncs_rpc_notif_alarm-text-t {
    type string {
      length "1..1024";
    }
    description
      "The string used to inform operators about the alarm. This MUST contain
       enough information for an operator to be able to understand the
       problem. If this string contains structure, this format should
       be clearly documented for programs to be able to parse that
       information.";
  }

  typedef ncs_rpc_notif_event-type {
    type enumeration {
      enum "other" {
        value 1;
      }
      enum "communicationsAlarm" {
        value 2;
      }
      enum "qualityOfServiceAlarm" {
        value 3;
      }
      enum "processingErrorAlarm" {
        value 4;
      }
      enum "equipmentAlarm" {
        value 5;
      }
      enum "environmentalAlarm" {
        value 6;
      }
      enum "integrityViolation" {
        value 7;
      }
      enum "operationalViolation" {
        value 8;
      }
      enum "physicalViolation" {
        value 9;
      }
      enum "securityServiceOrMechanismViolation" {
        value 10;
      }
      enum "timeDomainViolation" {
        value 11;
      }
    }
    reference
      "ITU Recommendation X.736, 'Information Technology - Open
       Systems Interconnection - System Management: Security
       Alarm Reporting Function', 1992";
  }

  typedef ncs_rpc_notif_severity-t {
    type enumeration {
      enum "cleared" {
        value 1;
      }
      enum "indeterminate" {
        value 2;
      }
      enum "minor" {
        value 3;
      }
      enum "warning" {
        value 4;
      }
      enum "major" {
        value 5;
      }
      enum "critical" {
        value 6;
      }
    }
    description
      "Severity of an alarm, including the cleared state";
  }

  typedef ncs_rpc_notif_alarm-handling-state-t {
    type enumeration {
      enum "none" {
        value 1;
      }
      enum "ack" {
        value 2;
      }
      enum "investigation" {
        value 3;
      }
      enum "observation" {
        value 4;
      }
      enum "closed" {
        value 5;
      }
    }
    description
      "Operator actions on alarms";
  }

  typedef ncs_rpc_notif_alarm-kind-t {
    type enumeration {
      enum "root-cause";
      enum "symptom";
      enum "unknown";
    }
  }

  typedef ncs_rpc_notif_alarm-type-t {
    // NCS patched to string, due to LSA partial NED
    type string;
  }

  typedef live_ncs_managed-object-t {
    type union {
      // NCS patched to string, due to LSA partial NED
      type string;
      type yang:object-identifier;
      type string;
    }
    description
      "If the referenced managed object is modelled in YANG, this type
       will be an instance-identifier.  If the managed object is an SNMP
       object, the type will be an object-identifier.  If the managed
       object is anything else, for example a distinguished name or a CIM
       path, this type will be a string.";
  }

  typedef live_ncs_alarm-text-t {
    type string {
      length "1..1024";
    }
    description
      "The string used to inform operators about the alarm. This MUST contain
       enough information for an operator to be able to understand the
       problem. If this string contains structure, this format should
       be clearly documented for programs to be able to parse that
       information.";
  }

  typedef live_ncs_event-type {
    type enumeration {
      enum "other" {
        value 1;
      }
      enum "communicationsAlarm" {
        value 2;
      }
      enum "qualityOfServiceAlarm" {
        value 3;
      }
      enum "processingErrorAlarm" {
        value 4;
      }
      enum "equipmentAlarm" {
        value 5;
      }
      enum "environmentalAlarm" {
        value 6;
      }
      enum "integrityViolation" {
        value 7;
      }
      enum "operationalViolation" {
        value 8;
      }
      enum "physicalViolation" {
        value 9;
      }
      enum "securityServiceOrMechanismViolation" {
        value 10;
      }
      enum "timeDomainViolation" {
        value 11;
      }
    }
    reference
      "ITU Recommendation X.736, 'Information Technology - Open
       Systems Interconnection - System Management: Security
       Alarm Reporting Function', 1992";
  }

  typedef live_ncs_severity-t {
    type enumeration {
      enum "cleared" {
        value 1;
      }
      enum "indeterminate" {
        value 2;
      }
      enum "minor" {
        value 3;
      }
      enum "warning" {
        value 4;
      }
      enum "major" {
        value 5;
      }
      enum "critical" {
        value 6;
      }
    }
    description
      "Severity of an alarm, including the cleared state";
  }

  typedef live_ncs_alarm-handling-state-t {
    type enumeration {
      enum "none" {
        value 1;
      }
      enum "ack" {
        value 2;
      }
      enum "investigation" {
        value 3;
      }
      enum "observation" {
        value 4;
      }
      enum "closed" {
        value 5;
      }
    }
    description
      "Operator actions on alarms";
  }

  typedef live_ncs_alarm-kind-t {
    type enumeration {
      enum "root-cause";
      enum "symptom";
      enum "unknown";
    }
  }

  typedef live_ncs_alarm-type-t {
    // NCS patched to string, due to LSA partial NED
    type string;
  }

  typedef managed-object-t {
    type union {
      // NCS patched to string, due to LSA partial NED
      type string;
      type yang:object-identifier;
      type string;
    }
    description
      "If the referenced managed object is modelled in YANG, this type
       will be an instance-identifier.  If the managed object is an SNMP
       object, the type will be an object-identifier.  If the managed
       object is anything else, for example a distinguished name or a CIM
       path, this type will be a string.";
  }

  typedef alarm-text-t {
    type string {
      length "1..1024";
    }
    description
      "The string used to inform operators about the alarm. This MUST contain
       enough information for an operator to be able to understand the
       problem. If this string contains structure, this format should
       be clearly documented for programs to be able to parse that
       information.";
  }

  typedef event-type {
    type enumeration {
      enum "other" {
        value 1;
      }
      enum "communicationsAlarm" {
        value 2;
      }
      enum "qualityOfServiceAlarm" {
        value 3;
      }
      enum "processingErrorAlarm" {
        value 4;
      }
      enum "equipmentAlarm" {
        value 5;
      }
      enum "environmentalAlarm" {
        value 6;
      }
      enum "integrityViolation" {
        value 7;
      }
      enum "operationalViolation" {
        value 8;
      }
      enum "physicalViolation" {
        value 9;
      }
      enum "securityServiceOrMechanismViolation" {
        value 10;
      }
      enum "timeDomainViolation" {
        value 11;
      }
    }
    reference
      "ITU Recommendation X.736, 'Information Technology - Open
       Systems Interconnection - System Management: Security
       Alarm Reporting Function', 1992";
  }

  typedef severity-t {
    type enumeration {
      enum "cleared" {
        value 1;
      }
      enum "indeterminate" {
        value 2;
      }
      enum "minor" {
        value 3;
      }
      enum "warning" {
        value 4;
      }
      enum "major" {
        value 5;
      }
      enum "critical" {
        value 6;
      }
    }
    description
      "Severity of an alarm, including the cleared state";
  }

  typedef alarm-handling-state-t {
    type enumeration {
      enum "none" {
        value 1;
      }
      enum "ack" {
        value 2;
      }
      enum "investigation" {
        value 3;
      }
      enum "observation" {
        value 4;
      }
      enum "closed" {
        value 5;
      }
    }
    description
      "Operator actions on alarms";
  }

  typedef alarm-kind-t {
    type enumeration {
      enum "root-cause";
      enum "symptom";
      enum "unknown";
    }
  }

  typedef alarm-type-t {
    // NCS patched to string, due to LSA partial NED
    type string;
  }

  grouping ncs_rpc_notif_common-alarm-parameters {
    description
      "Common parameters for an alarm.

       This grouping is used both in the active alarm list and in the
       notification representing an alarm state change.";
    leaf device {
      type string;
      description
        "If a managed device is associated to the alarm, this leaf
         is the name of that device.  All alarms may not
         be possible to associate to a specific device, thus
         this leaf is a string and not a leafref.

         For alarms associated with NCS, this leaf has the value 'ncs'.";
      tailf:info
        "The alarming device";
    }
    leaf type {
      type ncs_rpc_notif_alarm-type-t;
      description
        "This leaf and the leaf 'specific-problem', together provides a
         unique identification of the alarm type.

         Different managed object types and instances can share alarm
         types, but if the same managed object reports the same alarm
         type, it is to be considered as the same alarm state.";
      tailf:info
        "Unique identification of the alarm type";
    }
    leaf managed-object {
      type ncs_rpc_notif_managed-object-t;
      description
        "The alarming object.  See also 'alt-managed-object'.";
      tailf:info
        "The alarming object";
    }
    leaf specific-problem {
      type string;
      description
        "This leaf is used when the 'type' leaf cannot uniquely
         identify the alarm type.  Normally, this is not the case,
         and this leaf is the empty string.";
      tailf:info
        "Alarm type refinement";
    }
    leaf-list alt-managed-object {
      type ncs_rpc_notif_managed-object-t;
      description
        "Used if the alarming object is available over other interfaces.
         This field can contain SNMP OID's, CIM paths or 3GPP
         Distinguished names for example.";
      tailf:info
        "Alternate names for managed objects";
    }
    list related-alarms {
      key "device type managed-object";
      leaf device {
        type string;
        tailf:info
          "Alarms related to this alarm";
      }
      leaf type {
        type string;
      }
      leaf managed-object {
        type string;
      }
      leaf specific-problem {
        type string;
      }
    }
    leaf-list impacted-objects {
      type ncs_rpc_notif_managed-object-t;
      description
        "Objects that might be affected by this alarm";
      tailf:info
        "Objects that might be affected by this alarm";
    }
    leaf-list root-cause-objects {
      type ncs_rpc_notif_managed-object-t;
      description
        "Objects that are candidates for causing the alarm";
      tailf:info
        "Objects that are candidates for causing the alarm";
    }
  }

  grouping ncs_rpc_notif_alarm-state-change-parameters {
    description
      "Paramaters for an alarm state change.

       This grouping is used both in the active alarm list's
       status-change list and in the notification representing an
       alarm state change.";
    leaf event-time {
      type yang:date-and-time;
      description
        "The time the status of the alarm changed, as reported
         by the device.";
      tailf:info
        "Time stamp of state change as reported by the device";
    }
    leaf received-time {
      type yang:date-and-time;
      mandatory true;
      description
        "The time the status of the alarm changed, as detected
         by NCS.";
      tailf:info
        "Time stamp of state change as recevied by NCS";
    }
    leaf perceived-severity {
      type ncs_rpc_notif_severity-t;
      mandatory true;
      description
        "The severity of the alarm as defined by X.733.  Note that this
         may not be the original severity since the alarm may have
         changed severity.";
      tailf:info
        "The severity of this state change";
      reference
        "ITU Recommendation X.733, 'Information Technology - Open Systems
         Interconnection - System Management: Alarm Reporting
         Function', 1992";
    }
    leaf alarm-text {
      type ncs_rpc_notif_alarm-text-t;
      description
        "A user friendly text describing the alarm state change.";
      tailf:info
        "The alarm text of this state change";
      reference
        "Additional Text from ITU Recommendation X.733, 'Information
          Technology
          - Open Systems Interconnection - System Management: Alarm
          Reporting Function', 1992";
    }
  }

  grouping ncs_rpc_notif_alarm-model-parameters {
    description
      "Parameters used to map from NCS alarm types
       to X.733 and 3GPP alarm parameters.

       This grouping is used both in the alarm-model list and in the
       notification representing an alarm state change.";
    leaf event-type {
      type ncs_rpc_notif_event-type;
      mandatory true;
      description
        "The event type as defined in X.733/X.736.";
      tailf:info
        "The event type as defined in X.733/X.736.";
      reference
        "ITU Recommendation X.733, 'Information Technology - Open Systems
         Interconnection - System Management: Alarm Reporting
         Function', 1992";
    }
    leaf has-clear {
      type union {
        type boolean;
        type enumeration {
          enum "unknown" {
            value 2;
          }
        }
      }
      mandatory true;
      description
        "Indicates if the alarm has a potential clear notification.";
      tailf:info
        "Indicates if the alarm has a potential clear notification.";
    }
    leaf kind-of-alarm {
      type ncs_rpc_notif_alarm-kind-t;
      mandatory true;
      description
        "Indicates if the alarm is a root-cause or a symptom.";
      tailf:info
        "Indicates if the alarm is a root-cause or a symptom";
    }
    leaf probable-cause {
      type uint32;
      description
        "The probable cause for the alarm originally defined by X.733 and
         subsequent standards.  Due to the history of problems in
         maintaining a standardized probable cause the probable
         cause is not unique.  A best effort mapping of the alarm
         to existing probable causes are used.";
      tailf:info
        "The probable cause integer value";
      reference
        "ITU Recommendation X.733, 'Information Technology - Open Systems
         Interconnection - System Management: Alarm Reporting
         Function', 1992";
    }
  }

  grouping ncs_rpc_notif_alarm-summary-parameters {
    description
      "A set of parameters to summarize the alarm situation.";
    leaf indeterminates {
      type yang:gauge32;
      description
        "This object shows the number of currently active
         alarms with perceived severity 'indeterminate'.";
    }
    leaf criticals {
      type yang:gauge32;
      description
        "This object shows the number of currently active
         alarms with perceived severity 'critical'.";
    }
    leaf majors {
      type yang:gauge32;
      description
        "This object shows the number of currently active alarms with
         perceived severity 'major'.";
    }
    leaf minors {
      type yang:gauge32;
      description
        "This object shows the number of currently active
         alarms with perceived severity 'minor'.";
    }
    leaf warnings {
      type yang:gauge32;
      description
        "This object shows the number of currently active
          alarms with perceived severity 'warning'.";
    }
  }

  grouping live_ncs_common-alarm-parameters {
    description
      "Common parameters for an alarm.

       This grouping is used both in the active alarm list and in the
       notification representing an alarm state change.";
    leaf device {
      type string;
      description
        "If a managed device is associated to the alarm, this leaf
         is the name of that device.  All alarms may not
         be possible to associate to a specific device, thus
         this leaf is a string and not a leafref.

         For alarms associated with NCS, this leaf has the value 'ncs'.";
      tailf:info
        "The alarming device";
    }
    leaf type {
      type live_ncs_alarm-type-t;
      description
        "This leaf and the leaf 'specific-problem', together provides a
         unique identification of the alarm type.

         Different managed object types and instances can share alarm
         types, but if the same managed object reports the same alarm
         type, it is to be considered as the same alarm state.";
      tailf:info
        "Unique identification of the alarm type";
    }
    leaf managed-object {
      type live_ncs_managed-object-t;
      description
        "The alarming object.  See also 'alt-managed-object'.";
      tailf:info
        "The alarming object";
    }
    leaf specific-problem {
      type string;
      description
        "This leaf is used when the 'type' leaf cannot uniquely
         identify the alarm type.  Normally, this is not the case,
         and this leaf is the empty string.";
      tailf:info
        "Alarm type refinement";
    }
    leaf-list alt-managed-object {
      type live_ncs_managed-object-t;
      description
        "Used if the alarming object is available over other interfaces.
         This field can contain SNMP OID's, CIM paths or 3GPP
         Distinguished names for example.";
      tailf:info
        "Alternate names for managed objects";
    }
    list related-alarms {
      key "device type managed-object";
      leaf device {
        type leafref {
          path "/ncs-internal:devices/ncs-internal:device/ncs-internal:live-status/alarms/alarm-list/alarm/device" {
            tailf:xpath-root 3;
          }
        }
        tailf:info
          "Alarms related to this alarm";
      }
      leaf type {
        type leafref {
          path "deref(../device)/../type";
        }
      }
      leaf managed-object {
        type leafref {
          path "deref(../type)/../managed-object";
        }
      }
      leaf specific-problem {
        type leafref {
          path "deref(../type)/../specific-problem";
        }
      }
    }
    leaf-list impacted-objects {
      type live_ncs_managed-object-t;
      description
        "Objects that might be affected by this alarm";
      tailf:info
        "Objects that might be affected by this alarm";
    }
    leaf-list root-cause-objects {
      type live_ncs_managed-object-t;
      description
        "Objects that are candidates for causing the alarm";
      tailf:info
        "Objects that are candidates for causing the alarm";
    }
  }

  grouping live_ncs_alarm-state-change-parameters {
    description
      "Paramaters for an alarm state change.

       This grouping is used both in the active alarm list's
       status-change list and in the notification representing an
       alarm state change.";
    leaf event-time {
      type yang:date-and-time;
      description
        "The time the status of the alarm changed, as reported
         by the device.";
      tailf:info
        "Time stamp of state change as reported by the device";
    }
    leaf received-time {
      type yang:date-and-time;
      // NCS drop mandatory statement
      description
        "The time the status of the alarm changed, as detected
         by NCS.";
      tailf:info
        "Time stamp of state change as recevied by NCS";
    }
    leaf perceived-severity {
      type live_ncs_severity-t;
      // NCS drop mandatory statement
      description
        "The severity of the alarm as defined by X.733.  Note that this
         may not be the original severity since the alarm may have
         changed severity.";
      tailf:info
        "The severity of this state change";
      reference
        "ITU Recommendation X.733, 'Information Technology - Open Systems
         Interconnection - System Management: Alarm Reporting
         Function', 1992";
    }
    leaf alarm-text {
      type live_ncs_alarm-text-t;
      description
        "A user friendly text describing the alarm state change.";
      tailf:info
        "The alarm text of this state change";
      reference
        "Additional Text from ITU Recommendation X.733, 'Information
          Technology
          - Open Systems Interconnection - System Management: Alarm
          Reporting Function', 1992";
    }
  }

  grouping live_ncs_alarm-model-parameters {
    description
      "Parameters used to map from NCS alarm types
       to X.733 and 3GPP alarm parameters.

       This grouping is used both in the alarm-model list and in the
       notification representing an alarm state change.";
    leaf event-type {
      type live_ncs_event-type;
      // NCS drop mandatory statement
      description
        "The event type as defined in X.733/X.736.";
      tailf:info
        "The event type as defined in X.733/X.736.";
      reference
        "ITU Recommendation X.733, 'Information Technology - Open Systems
         Interconnection - System Management: Alarm Reporting
         Function', 1992";
    }
    leaf has-clear {
      type union {
        type boolean;
        type enumeration {
          enum "unknown" {
            value 2;
          }
        }
      }
      // NCS drop mandatory statement
      description
        "Indicates if the alarm has a potential clear notification.";
      tailf:info
        "Indicates if the alarm has a potential clear notification.";
    }
    leaf kind-of-alarm {
      type live_ncs_alarm-kind-t;
      // NCS drop mandatory statement
      description
        "Indicates if the alarm is a root-cause or a symptom.";
      tailf:info
        "Indicates if the alarm is a root-cause or a symptom";
    }
    leaf probable-cause {
      type uint32;
      description
        "The probable cause for the alarm originally defined by X.733 and
         subsequent standards.  Due to the history of problems in
         maintaining a standardized probable cause the probable
         cause is not unique.  A best effort mapping of the alarm
         to existing probable causes are used.";
      tailf:info
        "The probable cause integer value";
      reference
        "ITU Recommendation X.733, 'Information Technology - Open Systems
         Interconnection - System Management: Alarm Reporting
         Function', 1992";
    }
  }

  grouping live_ncs_alarm-summary-parameters {
    description
      "A set of parameters to summarize the alarm situation.";
    leaf indeterminates {
      type yang:gauge32;
      description
        "This object shows the number of currently active
         alarms with perceived severity 'indeterminate'.";
    }
    leaf criticals {
      type yang:gauge32;
      description
        "This object shows the number of currently active
         alarms with perceived severity 'critical'.";
    }
    leaf majors {
      type yang:gauge32;
      description
        "This object shows the number of currently active alarms with
         perceived severity 'major'.";
    }
    leaf minors {
      type yang:gauge32;
      description
        "This object shows the number of currently active
         alarms with perceived severity 'minor'.";
    }
    leaf warnings {
      type yang:gauge32;
      description
        "This object shows the number of currently active
          alarms with perceived severity 'warning'.";
    }
  }

  grouping common-alarm-parameters {
    description
      "Common parameters for an alarm.

       This grouping is used both in the active alarm list and in the
       notification representing an alarm state change.";
    leaf device {
      type string;
      description
        "If a managed device is associated to the alarm, this leaf
         is the name of that device.  All alarms may not
         be possible to associate to a specific device, thus
         this leaf is a string and not a leafref.

         For alarms associated with NCS, this leaf has the value 'ncs'.";
      tailf:info
        "The alarming device";
    }
    leaf type {
      type alarm-type-t;
      description
        "This leaf and the leaf 'specific-problem', together provides a
         unique identification of the alarm type.

         Different managed object types and instances can share alarm
         types, but if the same managed object reports the same alarm
         type, it is to be considered as the same alarm state.";
      tailf:info
        "Unique identification of the alarm type";
    }
    leaf managed-object {
      type managed-object-t;
      description
        "The alarming object.  See also 'alt-managed-object'.";
      tailf:info
        "The alarming object";
    }
    leaf specific-problem {
      type string;
      description
        "This leaf is used when the 'type' leaf cannot uniquely
         identify the alarm type.  Normally, this is not the case,
         and this leaf is the empty string.";
      tailf:info
        "Alarm type refinement";
    }
    leaf-list alt-managed-object {
      type managed-object-t;
      description
        "Used if the alarming object is available over other interfaces.
         This field can contain SNMP OID's, CIM paths or 3GPP
         Distinguished names for example.";
      tailf:info
        "Alternate names for managed objects";
    }
    list related-alarms {
      key "device type managed-object";
      leaf device {
        type leafref {
          path "/ncs-internal:devices/ncs-internal:device/ncs-internal:live-status/alarms/alarm-list/alarm/device" {
            tailf:xpath-root 2;
          }
        }
        tailf:info
          "Alarms related to this alarm";
      }
      leaf type {
        type leafref {
          path "deref(../device)/../type";
        }
      }
      leaf managed-object {
        type leafref {
          path "deref(../type)/../managed-object";
        }
      }
      leaf specific-problem {
        type leafref {
          path "deref(../type)/../specific-problem";
        }
      }
    }
    leaf-list impacted-objects {
      type managed-object-t;
      description
        "Objects that might be affected by this alarm";
      tailf:info
        "Objects that might be affected by this alarm";
    }
    leaf-list root-cause-objects {
      type managed-object-t;
      description
        "Objects that are candidates for causing the alarm";
      tailf:info
        "Objects that are candidates for causing the alarm";
    }
  }

  grouping alarm-state-change-parameters {
    description
      "Paramaters for an alarm state change.

       This grouping is used both in the active alarm list's
       status-change list and in the notification representing an
       alarm state change.";
    leaf event-time {
      type yang:date-and-time;
      description
        "The time the status of the alarm changed, as reported
         by the device.";
      tailf:info
        "Time stamp of state change as reported by the device";
    }
    leaf received-time {
      type yang:date-and-time;
      mandatory true;
      description
        "The time the status of the alarm changed, as detected
         by NCS.";
      tailf:info
        "Time stamp of state change as recevied by NCS";
    }
    leaf perceived-severity {
      type severity-t;
      mandatory true;
      description
        "The severity of the alarm as defined by X.733.  Note that this
         may not be the original severity since the alarm may have
         changed severity.";
      tailf:info
        "The severity of this state change";
      reference
        "ITU Recommendation X.733, 'Information Technology - Open Systems
         Interconnection - System Management: Alarm Reporting
         Function', 1992";
    }
    leaf alarm-text {
      type alarm-text-t;
      description
        "A user friendly text describing the alarm state change.";
      tailf:info
        "The alarm text of this state change";
      reference
        "Additional Text from ITU Recommendation X.733, 'Information
          Technology
          - Open Systems Interconnection - System Management: Alarm
          Reporting Function', 1992";
    }
  }

  grouping alarm-model-parameters {
    description
      "Parameters used to map from NCS alarm types
       to X.733 and 3GPP alarm parameters.

       This grouping is used both in the alarm-model list and in the
       notification representing an alarm state change.";
    leaf event-type {
      type event-type;
      mandatory true;
      description
        "The event type as defined in X.733/X.736.";
      tailf:info
        "The event type as defined in X.733/X.736.";
      reference
        "ITU Recommendation X.733, 'Information Technology - Open Systems
         Interconnection - System Management: Alarm Reporting
         Function', 1992";
    }
    leaf has-clear {
      type union {
        type boolean;
        type enumeration {
          enum "unknown" {
            value 2;
          }
        }
      }
      mandatory true;
      description
        "Indicates if the alarm has a potential clear notification.";
      tailf:info
        "Indicates if the alarm has a potential clear notification.";
    }
    leaf kind-of-alarm {
      type alarm-kind-t;
      mandatory true;
      description
        "Indicates if the alarm is a root-cause or a symptom.";
      tailf:info
        "Indicates if the alarm is a root-cause or a symptom";
    }
    leaf probable-cause {
      type uint32;
      description
        "The probable cause for the alarm originally defined by X.733 and
         subsequent standards.  Due to the history of problems in
         maintaining a standardized probable cause the probable
         cause is not unique.  A best effort mapping of the alarm
         to existing probable causes are used.";
      tailf:info
        "The probable cause integer value";
      reference
        "ITU Recommendation X.733, 'Information Technology - Open Systems
         Interconnection - System Management: Alarm Reporting
         Function', 1992";
    }
  }

  grouping alarm-summary-parameters {
    description
      "A set of parameters to summarize the alarm situation.";
    leaf indeterminates {
      type yang:gauge32;
      description
        "This object shows the number of currently active
         alarms with perceived severity 'indeterminate'.";
    }
    leaf criticals {
      type yang:gauge32;
      description
        "This object shows the number of currently active
         alarms with perceived severity 'critical'.";
    }
    leaf majors {
      type yang:gauge32;
      description
        "This object shows the number of currently active alarms with
         perceived severity 'major'.";
    }
    leaf minors {
      type yang:gauge32;
      description
        "This object shows the number of currently active
         alarms with perceived severity 'minor'.";
    }
    leaf warnings {
      type yang:gauge32;
      description
        "This object shows the number of currently active
          alarms with perceived severity 'warning'.";
    }
  }

  augment "/ncs-internal:devices/ncs-internal:device/ncs-internal:notifications/ncs-internal:received-notifications/ncs-internal:notification/ncs-internal:data" {
    container alarm-notification {
      presence "";
      config false;
      description
        "This notification is used to report a state change for an alarm.  The
         same notification is used for sending a new alarm, a cleared
         alarm or changing the text and/or severity of an existing
         alarm.

         A receiving NETCONF client shall use the 'device', 'type',
         'managed-object' and 'specific-problem' to match against
         existing alarms.";
      leaf alarm-class {
        type enumeration {
          enum "new-alarm" {
            description
              "The alarm has not yet changed and has not been cleared.";
          }
          enum "changed-alarm" {
            description
              "The alarm has changed but has not been cleared.";
          }
          enum "cleared-alarm" {
            description
              "The alarm has been cleared.";
          }
        }
        description
          "Specifies if this notification is a new, changed or cleared alarm,";
        reference "3GPP TS 32.111-2 - notificationType";
      }
      uses ncs_rpc_notif_common-alarm-parameters;
      uses ncs_rpc_notif_alarm-model-parameters;
      uses ncs_rpc_notif_alarm-state-change-parameters;
    }
  }
  augment "/ncs-internal:devices/ncs-internal:device/ncs-internal:netconf-notifications/ncs-internal:received-notifications/ncs-internal:notification/ncs-internal:data" {
    container alarm-notification {
      presence "";
      config false;
      description
        "This notification is used to report a state change for an alarm.  The
         same notification is used for sending a new alarm, a cleared
         alarm or changing the text and/or severity of an existing
         alarm.

         A receiving NETCONF client shall use the 'device', 'type',
         'managed-object' and 'specific-problem' to match against
         existing alarms.";
      leaf alarm-class {
        type enumeration {
          enum "new-alarm" {
            description
              "The alarm has not yet changed and has not been cleared.";
          }
          enum "changed-alarm" {
            description
              "The alarm has changed but has not been cleared.";
          }
          enum "cleared-alarm" {
            description
              "The alarm has been cleared.";
          }
        }
        description
          "Specifies if this notification is a new, changed or cleared alarm,";
        reference "3GPP TS 32.111-2 - notificationType";
      }
      uses ncs_rpc_notif_common-alarm-parameters;
      uses ncs_rpc_notif_alarm-model-parameters;
      uses ncs_rpc_notif_alarm-state-change-parameters;
    }
  }
  augment "/ncs-internal:devices/ncs-internal:device/ncs-internal:config" {
    container alarms {
      tailf:ncs-device-type "netconf";
      tailf:display-when "not(../../ncs-internal:module) or ../../ncs-internal:module[ncs-internal:name='tailf-ncs-alarms']";
      tailf:info
        "Alarm management";
      container control {
        tailf:info
          "Alarm control";
        leaf filter-level {
          type severity-t;
        }
        leaf max-status-change-entries-per-alarm {
          type int32;
          default "32";
          description
            "The status-change entries are kept in a circular queue.
             When this number is exceeded, the oldest status change
             entry is automatically removed. If the value is 0, the
             status change entries are accumulated indefinitely";
          tailf:info
            "Max number of state changes per alarm, 0 indefinitely";
        }
        leaf notify-about-status-changes {
          type boolean;
          default "false";
          description
            "This leaf controls whether NETCONF notifications and SNMP
             traps will be sent on any alarm status updates, e.g. updated
             perceived-severity or alarm-text. By default the notifications
             are only sent when a new alarm is raised, re-raised after being
             cleared, and when an alarm is cleared.";
          tailf:info
            "Notify NETCONF/SNMP about all alarm status changes";
        }
        leaf notify-cli {
          type boolean;
          default "true";
          description
            "This leaf controls whether a message is sent to all CLI
             sessions when an alarm is raised or re-raised after being
             cleared.";
          tailf:info
            "Notify CLI sessions about raised alarms";
        }
      }
      container alarm-model {
        tailf:info
          "Configure how alarms are sent northbound with X.733 mapping";
        list alarm-type {
          key "type specific-problem-match";
          ordered-by user;
          description
            "This list is used to define a mapping from NCS alarm types
             to X.733 and 3GPP alarm parameters.

             Specific problem is a refinement of alarm-type.  It can be used
             in the mapping process by specifying a regular expression.

             When NCS generates an alarm, it looks up the type of the
             alarm in this list.  For each entry with this type, NCS
             checks the specific problem, in the order the entries
             appears in the list.  If the specific-problem-match
             matches the specific-match of the alarm, NCS uses this
             entry and discards the rest.

             If an entry is found, the parameters defined here are used
             in the alarm notification, when sent as a NETCONF
             notification or SNMP notification.  If no entry is found,
             default values are used in the notifications.";
          leaf type {
            type alarm-type-t;
            description
              "This provides a unique identification of the alarm type.";
            tailf:info
              "Map this alarm type";
          }
          leaf specific-problem-match {
            tailf:key-default "*";
            type string;
            tailf:cli-disallow-value "event-type|has-clear|kind-of-alarm|probable-cause";
            description
              "A W3C regular expression that is used when mapping an alarm
               type and specific problem to X.733 parameters.";
            tailf:info
              "Regular expression to match a specific problem";
          }
          uses alarm-model-parameters;
        }
      }
      // NCS drop config false container summary
      // NCS drop config false container 'alarm-list'
      tailf:action synchronize-alarms {
        tailf:actionpoint ncsproxy {
          tailf:internal;
        }
        tailf:info
          "Synchronize the alarm state from the device";
        // NCS drop tailf:actionpoint
        description
          "This action requests the server to synchronize its alarm list versus
           the resources. It can be viewed as an audit function to
           verify the current view of the alarm status.  Support for
           this rpc depends on the mechanisms of the NETCONF server to
           maintain the alarm list. In a theoretical sense an alarm list
           is operational data and therefore requests to read the alarm
           list should always return the active alarms from the
           resources and this rpc would then be superfluous. This will be
           true for many systems.  The number of created, deleted, and
           changed alarms are returned as output parameters.  Also, the
           corresponding notifications shall be sent.";
        output {
          leaf result {
            type string;
          }
          leaf new-alarms {
            type uint16;
          }
          leaf changed-alarms {
            type uint16;
          }
          leaf cleared-alarms {
            type uint16;
          }
        }
      }
      tailf:action compress-alarms {
        tailf:actionpoint ncsproxy {
          tailf:internal;
        }
        tailf:info
          "Compress the history of state changes for each alarm";
        // NCS drop tailf:actionpoint
        description
          "This action requests the server to compress the alarm entries by
           removing the history of each individual alarm. The latest state
           change will be kept. Note that no alarm entries as such are removed
           only the history for each alarm.";
        output {
          leaf result {
            type string;
          }
          leaf compressed-elements {
            type uint16;
          }
        }
      }

      grouping filter-input {
        leaf alarm-status {
          type enumeration {
            enum "any";
            enum "cleared";
            enum "not-cleared";
          }
          mandatory true;
        }
        container older-than {
          presence "Age specification";
          description
            "Matches the 'last-status-change' leaf in the alarm.";
          choice age-spec {
            case seconds {
              leaf seconds {
                type uint16;
              }
            }
            case minutes {
              leaf minutes {
                type uint16;
              }
            }
            case hours {
              leaf hours {
                type uint16;
              }
            }
            case days {
              leaf days {
                type uint16;
              }
            }
            case weeks {
              leaf weeks {
                type uint16;
              }
            }
          }
        }
        container severity {
          presence "Severity filter";
          choice sev-spec {
            leaf below {
              type severity-t;
            }
            leaf is {
              type severity-t;
            }
            leaf above {
              type severity-t;
            }
          }
        }
        container alarm-handling-state-filter {
          presence "Operator state filter";
          leaf state {
            type alarm-handling-state-t;
          }
          leaf user {
            type string;
          }
        }
      }
      tailf:action filter-alarms {
        tailf:actionpoint ncsproxy {
          tailf:internal;
        }
        // NCS drop tailf:actionpoint
        description
          "This action returns the keys of all alarms matching the filter
           criteria";
        tailf:info
          "Show the keys for all alarm matching the criteria";
        input {
          uses filter-input;
        }
        output {
          list filtered-key {
            leaf device {
              type string;
            }
            leaf type {
              type alarm-type-t;
            }
            leaf managed-object {
              type managed-object-t;
            }
            leaf specific-problem {
              type string;
            }
          }
        }
      }
      tailf:action purge-alarms {
        tailf:actionpoint ncsproxy {
          tailf:internal;
        }
        tailf:info
          "Remove alarms";
        // NCS drop tailf:actionpoint
        description
          "This action requests the server to delete entries from the alarm list
           according to the supplied criteria. Typically it can be used
           to delete alarms that are in cleared state and older than a
           specified time.  The number of purged alarms is returned as
           an output parameter";
        input {
          uses filter-input;
        }
        output {
          leaf result {
            type string;
          }
          leaf purged-alarms {
            type uint16;
          }
        }
      }
    }
  }
  augment "/ncs-internal:devices/ncs-internal:device/ncs-internal:live-status" {
    container alarms {
      tailf:ncs-device-type "netconf";
      tailf:display-when "not(../../ncs-internal:module) or ../../ncs-internal:module[ncs-internal:name='tailf-ncs-alarms'] or (../../ncs-internal:live-status-protocol[not(ncs-internal:capability)]) or (../../ncs-internal:live-status-protocol/ncs-internal:capability/ncs-internal:module[.='tailf-ncs-alarms'])";
      tailf:info
        "Alarm management";
      container control {
        tailf:info
          "Alarm control";
        leaf filter-level {
          type live_ncs_severity-t;
        }
        leaf max-status-change-entries-per-alarm {
          type int32;
          // NCS drop default statement
          description
            "The status-change entries are kept in a circular queue.
             When this number is exceeded, the oldest status change
             entry is automatically removed. If the value is 0, the
             status change entries are accumulated indefinitely";
          tailf:info
            "Max number of state changes per alarm, 0 indefinitely";
        }
        leaf notify-about-status-changes {
          type boolean;
          // NCS drop default statement
          description
            "This leaf controls whether NETCONF notifications and SNMP
             traps will be sent on any alarm status updates, e.g. updated
             perceived-severity or alarm-text. By default the notifications
             are only sent when a new alarm is raised, re-raised after being
             cleared, and when an alarm is cleared.";
          tailf:info
            "Notify NETCONF/SNMP about all alarm status changes";
        }
        leaf notify-cli {
          type boolean;
          // NCS drop default statement
          description
            "This leaf controls whether a message is sent to all CLI
             sessions when an alarm is raised or re-raised after being
             cleared.";
          tailf:info
            "Notify CLI sessions about raised alarms";
        }
      }
      container alarm-model {
        tailf:info
          "Configure how alarms are sent northbound with X.733 mapping";
        list alarm-type {
          key "type specific-problem-match";
          ordered-by user;
          description
            "This list is used to define a mapping from NCS alarm types
             to X.733 and 3GPP alarm parameters.

             Specific problem is a refinement of alarm-type.  It can be used
             in the mapping process by specifying a regular expression.

             When NCS generates an alarm, it looks up the type of the
             alarm in this list.  For each entry with this type, NCS
             checks the specific problem, in the order the entries
             appears in the list.  If the specific-problem-match
             matches the specific-match of the alarm, NCS uses this
             entry and discards the rest.

             If an entry is found, the parameters defined here are used
             in the alarm notification, when sent as a NETCONF
             notification or SNMP notification.  If no entry is found,
             default values are used in the notifications.";
          leaf type {
            type live_ncs_alarm-type-t;
            description
              "This provides a unique identification of the alarm type.";
            tailf:info
              "Map this alarm type";
          }
          leaf specific-problem-match {
            tailf:key-default "*";
            type string;
            // NCS drop tailf:cli-disallow-value
            description
              "A W3C regular expression that is used when mapping an alarm
               type and specific problem to X.733 parameters.";
            tailf:info
              "Regular expression to match a specific problem";
          }
          uses live_ncs_alarm-model-parameters;
        }
      }
      container summary {
        description
          "A global summary of all alarms in the system.";
        tailf:info
          "Number of alarms per severity";
        uses live_ncs_alarm-summary-parameters;
      }
      container alarm-list {
        tailf:info
          "Show the alarm list";
        leaf number-of-alarms {
          tailf:info
            "Number of alarms";
          type yang:gauge32;
          // NCS drop default statement
          description
            "This object shows the total number of currently
             alarms, i.e. the total number of entries
             in the alarm list.";
        }
        leaf last-changed {
          type yang:date-and-time;
          description
            "A timestamp when the active alarm list was last
             changed. The value can be used by a manager to
             initiate an alarm resynchronization procedure.";
          tailf:info
            "Time stamp when the alarm list was last changed";
        }
        list alarm {
          key "device type managed-object specific-problem";
          description
            "The list of alarms.  Each entry in the list holds one
             alarm for a given alarm type and device, managed object.
             An alarm can be updated from the underlying device or
             by the user. These changes are reflected in different lists
             below the corresponding alarm.";
          uses live_ncs_common-alarm-parameters;
          // NCS drop fully hidden leaf 'snmp-index'
          leaf is-cleared {
            tailf:info
              "Is the alarm cleared by the underlying resource?";
            type boolean;
            // NCS drop mandatory statement
            description
              "Indicates the clearance state of the alarm.  An alarm might
               toggle from active alarm to cleared alarm and back to
               active again.  This leaf reflects the perceived severity
               in the latest entry in the status-change list.";
          }
          leaf last-status-change {
            tailf:info
              "Time of last status change from the underlying resource";
            type yang:date-and-time;
            // NCS drop mandatory statement
            description
              "A timestamp when the status-change list was last changed.
               This value equals the latest 'when' leaf in the
               status-change list.  The value can be used by a manager
               to read the last status change without iterating the
               status-change list below.";
          }
          leaf last-perceived-severity {
            tailf:info
              "Severity of the last status-change not equal to clear";
            type live_ncs_severity-t;
            description
              "The severity of the last status-change that
               reported a severity that is not equal to cleared.";
          }
          leaf last-alarm-text {
            tailf:info
              "Severity of the last alarm text not equal to clear";
            type live_ncs_alarm-text-t;
            description
              "The alarm-text of the last status-change that
               reported a severity that is not equal to cleared.";
          }
          list status-change {
            tailf:info
              "A list of status change events for this alarm";
            key "event-time";
            // NCS drop min-elements statement
            description
              "A list of status change events for this alarm.

               This list is ordered according to the timestamps of alarm
               state changes. The last item corresponds to the latest
               state change.";
            uses live_ncs_alarm-state-change-parameters;
          }
          leaf last-alarm-handling-change {
            type yang:date-and-time;
            description
              "A timestamp when the status-change list was last
               changed. The value can be used by a manager to
               read the last alarm-handling change without iterating the
               alarm-handling list below";
          }
          list alarm-handling {
            tailf:info
              "A list of operator actions for this alarm";
            key "time";
            description
              "This list is used by operators to indicate
               the state of human intervention on an alarm. For example,
               if an operator has seen an alarm, the operator can add
               a new item to this list indicating that the alarm is
               acknowledged";
            leaf time {
              tailf:info
                "Time stamp for operator acdtion";
              type yang:date-and-time;
              description
                "Timestamp for operator action on alarm.";
            }
            leaf state {
              tailf:info
                "The operators view of the alarm state";
              type live_ncs_alarm-handling-state-t;
              // NCS drop mandatory statement
              description
                "The operators view of the alarm state.";
            }
            leaf user {
              tailf:info
                "The name of the user that has operated on this alarm";
              type string;
              // NCS drop mandatory statement
              description
                "The name of the user that has operated on this alarm.";
            }
            leaf description {
              tailf:info
                "Free form textual description";
              type string;
              description
                "Additional optional textual information regarding
                 this new alarm-handling entry.";
            }
          }
          tailf:action purge {
            tailf:actionpoint ncsproxy {
              tailf:internal;
            }
            description
              "Delete this alarm.";
            tailf:info
              "Delete this alarm";
            // NCS drop tailf:actionpoint
          }
          tailf:action compress {
            tailf:actionpoint ncsproxy {
              tailf:internal;
            }
            tailf:info
              "Compress the history of state changes for this alarm";
            // NCS drop tailf:actionpoint
            description
              "This action requests the server to compress the alarm entry by
               removing the history of this alarm. The latest state
               change will be kept.";
            output {
              leaf result {
                type string;
              }
              leaf compressed-elements {
                type uint16;
              }
            }
          }
          tailf:action handle-alarm {
            tailf:actionpoint ncsproxy {
              tailf:internal;
            }
            tailf:info
              "Set the operator state of this alarm";
            description
              "An action to allow the operator to add an entry to the
               alarm-handling list. This is a means for the operator to indicate
               the level of human intervention on an alarm.";
            // NCS drop tailf:actionpoint
            input {
              leaf state {
                type live_ncs_alarm-handling-state-t;
                mandatory true;
              }
              leaf description {
                type string;
                description
                  "Additional optional textual information regarding
                   this new alarm-handling entry.";
              }
            }
          }
        }
      }
      tailf:action synchronize-alarms {
        tailf:actionpoint ncsproxy {
          tailf:internal;
        }
        tailf:info
          "Synchronize the alarm state from the device";
        // NCS drop tailf:actionpoint
        description
          "This action requests the server to synchronize its alarm list versus
           the resources. It can be viewed as an audit function to
           verify the current view of the alarm status.  Support for
           this rpc depends on the mechanisms of the NETCONF server to
           maintain the alarm list. In a theoretical sense an alarm list
           is operational data and therefore requests to read the alarm
           list should always return the active alarms from the
           resources and this rpc would then be superfluous. This will be
           true for many systems.  The number of created, deleted, and
           changed alarms are returned as output parameters.  Also, the
           corresponding notifications shall be sent.";
        output {
          leaf result {
            type string;
          }
          leaf new-alarms {
            type uint16;
          }
          leaf changed-alarms {
            type uint16;
          }
          leaf cleared-alarms {
            type uint16;
          }
        }
      }
      tailf:action compress-alarms {
        tailf:actionpoint ncsproxy {
          tailf:internal;
        }
        tailf:info
          "Compress the history of state changes for each alarm";
        // NCS drop tailf:actionpoint
        description
          "This action requests the server to compress the alarm entries by
           removing the history of each individual alarm. The latest state
           change will be kept. Note that no alarm entries as such are removed
           only the history for each alarm.";
        output {
          leaf result {
            type string;
          }
          leaf compressed-elements {
            type uint16;
          }
        }
      }

      grouping filter-input {
        leaf alarm-status {
          type enumeration {
            enum "any";
            enum "cleared";
            enum "not-cleared";
          }
          // NCS drop mandatory statement
        }
        container older-than {
          presence "Age specification";
          description
            "Matches the 'last-status-change' leaf in the alarm.";
          choice age-spec {
            case seconds {
              leaf seconds {
                type uint16;
              }
            }
            case minutes {
              leaf minutes {
                type uint16;
              }
            }
            case hours {
              leaf hours {
                type uint16;
              }
            }
            case days {
              leaf days {
                type uint16;
              }
            }
            case weeks {
              leaf weeks {
                type uint16;
              }
            }
          }
        }
        container severity {
          presence "Severity filter";
          choice sev-spec {
            leaf below {
              type live_ncs_severity-t;
            }
            leaf is {
              type live_ncs_severity-t;
            }
            leaf above {
              type live_ncs_severity-t;
            }
          }
        }
        container alarm-handling-state-filter {
          presence "Operator state filter";
          leaf state {
            type live_ncs_alarm-handling-state-t;
          }
          leaf user {
            type string;
          }
        }
      }
      tailf:action filter-alarms {
        tailf:actionpoint ncsproxy {
          tailf:internal;
        }
        // NCS drop tailf:actionpoint
        description
          "This action returns the keys of all alarms matching the filter
           criteria";
        tailf:info
          "Show the keys for all alarm matching the criteria";
        input {
          uses filter-input;
        }
        output {
          list filtered-key {
            leaf device {
              type string;
            }
            leaf type {
              type live_ncs_alarm-type-t;
            }
            leaf managed-object {
              type live_ncs_managed-object-t;
            }
            leaf specific-problem {
              type string;
            }
          }
        }
      }
      tailf:action purge-alarms {
        tailf:actionpoint ncsproxy {
          tailf:internal;
        }
        tailf:info
          "Remove alarms";
        // NCS drop tailf:actionpoint
        description
          "This action requests the server to delete entries from the alarm list
           according to the supplied criteria. Typically it can be used
           to delete alarms that are in cleared state and older than a
           specified time.  The number of purged alarms is returned as
           an output parameter";
        input {
          uses filter-input;
        }
        output {
          leaf result {
            type string;
          }
          leaf purged-alarms {
            type uint16;
          }
        }
      }
    }
  }
  augment "/ncs-internal:devices/ncs-internal:device/ncs-internal:live-status/ncs:devices/ncs:device" {
    container alarm-summary {
      tailf:ncs-device-type "netconf";
      tailf:display-when "not(../../ncs-internal:module) or ../../ncs-internal:module[ncs-internal:name='tailf-ncs-alarms'] or (../../ncs-internal:live-status-protocol[not(ncs-internal:capability)]) or (../../ncs-internal:live-status-protocol/ncs-internal:capability/ncs-internal:module[.='tailf-ncs-alarms'])";
      description
        "A summary of all active alarms per device.";
      tailf:info
        "A summary of all active alarms per device.";
      uses live_ncs_alarm-summary-parameters;
    }
  }
  augment "/ncs-internal:devices/ncs-internal:device/ncs-internal:config/ncs:devices/ncs:device" {
    // NCS drop config false container 'alarm-summary'
  }
  augment "/ncs-internal:devices/ncs-internal:device/ncs-internal:live-status/ncs:devices/ncs:device-group" {
    container alarm-summary {
      tailf:ncs-device-type "netconf";
      tailf:display-when "not(../../ncs-internal:module) or ../../ncs-internal:module[ncs-internal:name='tailf-ncs-alarms'] or (../../ncs-internal:live-status-protocol[not(ncs-internal:capability)]) or (../../ncs-internal:live-status-protocol/ncs-internal:capability/ncs-internal:module[.='tailf-ncs-alarms'])";
      description
        "A summary of all active alarms per device group.";
      tailf:info
        "A summary of all active alarms per device group.";
      uses live_ncs_alarm-summary-parameters;
    }
  }
  augment "/ncs-internal:devices/ncs-internal:device/ncs-internal:config/ncs:devices/ncs:device-group" {
    // NCS drop config false container 'alarm-summary'
  }

  identity cluster-subscriber-failure {
    base ncs-cluster-alarm;
    description
      "Failure to establish a notification subscription towards
       a remote node.
       * Severity:
         critical
       * Action:
         Verify IP connectivity between cluster nodes.
       * Message:
         Failed to establish netconf notification
         subscription to node ~s, stream ~s
       * Message:
         Commit queue items with remote nodes will not receive required
         event notifications.
       * Clear condition(s):
         This alarm is cleared if NCS succeeds to establish a
         subscription towards the remote node, or when the subscription
         is explicitly stopped.";
  }

  identity receiver-configuration-error {
    base ncs-snmp-notification-receiver-alarm;
    description
      "The snmp-notification-receiver could not setup its configuration,
       either at startup or when reconfigured. Snmp notifications will now
       be missed.
       * Severity:
         major
       * Action:
         Check the error-message and change the configuration.
       * Message:
         Configuration has errors.
       * Clear condition(s):
         This alarm will be cleared when the NCS is configured
         to successfully receive SNMP notifications";
  }

  identity ncs-snmp-notification-receiver-alarm {
    base alarm-type;
    description
      "Base type for SNMP notification receiver Alarms. This is never
       reported, sub-identities for specific SNMP notification receiver
       alarms are used in the alarms.";
  }

  identity package-operation-failure {
    base ncs-package-alarm;
    description
      "A package has some problem with its operation.
       * Severity:
         critical
       * Action:
         Check the package for the reason.
       * Clear condition(s):
         This alarm is not cleared.";
  }

  identity package-load-failure {
    base ncs-package-alarm;
    description
      "NCS failed to load a package.
       * Severity:
         critical
       * Action:
         Check the package for the reason.
       * Message:
         Specific to the concerned package.
       * Clear condition(s):
         If NCS successfully loads a package for which an alarm
         was previously raised, it will be cleared.";
  }

  identity service-activation-failure {
    base ncs-service-manager-alarm;
    description
      "A service failed during re-deploy.
       * Severity:
         critical
       * Action:
         Corrective action and another re-deploy is needed.
       * Clear condition(s):
         If the service is successfully redeployed, the alarm is cleared.";
  }

  identity bad-user-input {
    base ncs-dev-manager-alarm;
    description
      "Invalid input from user. NCS cannot recognize parameters needed to
       connect to device.
       * Severity:
        critical
       * Action:
        Verify that the user supplied input are correct.
       * Clear condition(s):
        This alarm is not cleared.";
  }

  identity missing-transaction-id {
    base ncs-dev-manager-alarm;
    description
      "A device announced in its NETCONF hello message that
       it supports the transaction-id as defined in
       http://tail-f.com/yang/netconf-monitoring.  However when
       NCS tries to read the transaction-id no data is returned.
       The NCS check-sync feature will not work. This is usually
       a case of misconfigured NACM rules on the managed device.
       * Severity:
        warning
       * Action:
        Verify NACM rules on the concerned device.
       * Clear condition(s):
        If NCS successfully reads a transaction id for which
        it had previously failed to do so, the alarm is cleared.";
  }

  identity commit-through-queue-rollback-failed {
    base ncs-dev-manager-alarm;
    description
      "Rollback of a commit-queue item failed.
       * Severity:
         critical
       * Action:
         Investigate the status of the device and resolve the
         situation by issuing the appropriate action, i.e., service
         redeploy or a sync operation.
       * Clear condition(s):
         This alarm is not cleared.";
  }

  identity commit-through-queue-blocked {
    base ncs-dev-manager-alarm;
    description
      "A commit was queued behind a queue item waiting to be able to
       connect to one of its devices. This is potentially dangerous
       since one unreachable device can potentially fill up the commit
       queue indefinitely.
       * Severity:
         warning
       * Message:
         Commit queue item ~p is blocked because item ~p cannot connect to ~s
       * Clear condition(s):
         An alarm raised due to a transient error will be cleared
         when NCS is able to reconnect to the device";
  }

  identity commit-through-queue-failed {
    base ncs-dev-manager-alarm;
    description
      "A queued commit failed.
       * Severity:
         critical
       * Action:
         Resolve with rollback if possible.
       * Message:
         Commit queue item {CqId} rollback invoked
       * Message:
         Commit queue item {CqId} has failed: Operation failed because:
         inconsistent database
       * Message:
         Remote commit queue item ~p cannot be unlocked:
         cluster node not configured correctly
       * Clear condition(s):
         This alarm is not cleared.";
  }

  identity configuration-error {
    base ncs-dev-manager-alarm;
    description
      "Invalid configuration of NCS managed device, NCS cannot recognize
       parameters needed to connect to device.
       * Severity:
        critical
       * Action:
        Verify that the configuration parameters defined in
        tailf-ncs-devices.yang submodule are consistent for this device.
       * Clear condition(s):
        The alarm is cleared when NCS reads the configuration
        parameters for the device, and is raised again if the
        parameters are invalid";
  }

  identity ned-live-tree-connection-failure {
    base ncs-dev-manager-alarm;
    description
      "NCS failed to connect to a managed device using one of the optional
       live-status-protocol NEDs.
       * Severity:
         major
       * Action:
         Verify the configuration of the optional NEDs.
         If the error occurs intermittently, increase connect-timeout.
       * Clear condition(s):
         If NCS successfully reconnects to the managed device,
         the alarm is cleared.";
  }

  identity dev-manager-internal-error {
    base ncs-dev-manager-alarm;
    status deprecated;
    description
      "An internal error in NCS device manager. It might happen due to
       unexpected device behaviour, or other unexpected condition.
       * Action:
         Report to the support team, provide NCS error log together
         with other available NCS logs.";
  }

  identity final-commit-error {
    base ncs-dev-manager-alarm;
    description
      "A managed device validated a configuration change, but failed to
       commit.  When this happens, NCS and the device are out of sync.
       * Severity:
         critical
       * Action:
         Reconcile by comparing and sync-from or sync-to.
       * Clear condition(s):
         This alarm is not cleared.";
  }

  identity out-of-sync {
    base ncs-dev-manager-alarm;
    description
      "A managed device is out of sync with NCS. Usually it means that the
       device has been configured out of band from NCS point of view.
       * Severity:
         major
       * Action:
         Inspect the difference with compare-config, reconcile by
         invoking sync-from or sync-to.
       * Message:
         Device {dev} is out of sync
       * Message:
         Out of sync due to no-networking or failed commit-queue commits.
       * Message:
         got: ~s expected: ~s.
       * Clear condition(s):
         If NCS achieves sync with a device, the alarm is cleared.";
  }

  identity revision-error {
    base ncs-dev-manager-alarm;
    description
      "A managed device arrived with a known module, but too new revision.
       * Severity:
         major
       * Action:
         Upgrade the Device NED using the new YANG revision in order
         to use the new features in the device.
       * Message:
          YANG module '{Module}' has an unsupported revision {Rev1},
           Ncs supports {Rev2}
       * Clear condition(s):
         If all device yang modules are supported by NCS,
         the alarm is cleared.";
  }

  identity abort-error {
    base ncs-dev-manager-alarm;
    description
      "An error happened while aborting or reverting a transaction. Device's
       configuration is likely to be inconsistent with the NCS CDB.
       * Severity:
         major
       * Action:
         Inspect the configuration difference with compare-config,
         resolve conflicts with sync-from or sync-to if any.
       * Message:
         abort error
       * Clear condition(s):
         If NCS achieves sync with the device, or receives a transaction
         id for a netconf session towards the device, the alarm is cleared.";
  }

  identity connection-failure {
    base ncs-dev-manager-alarm;
    description
      "NCS failed to connect to a managed device before the timeout expired.
       * Severity:
         major
       * Action:
         Verify address, port, authentication, check that the device is up
         and running. If the error occurs intermittently, increase
         connect-timeout.
       * Clear condition(s):
         If NCS successfully reconnects to the device, the alarm is cleared.";
  }

  identity ncs-cluster-alarm {
    base alarm-type;
    description
      "Base type for all alarms related to cluster.
       This is never reported, sub-identities for the specific
       cluster alarms are used in the alarms.";
  }

  identity ncs-package-alarm {
    base alarm-type;
    description
      "Base type for all alarms related to packages.
       This is never reported, sub-identities for the specific
       package alarms are used in the alarms.";
  }

  identity ncs-service-manager-alarm {
    base alarm-type;
    description
      "Base type for all alarms related to the service manager
       This is never reported, sub-identities for the specific
       service alarms are used in the alarms.";
  }

  identity ncs-dev-manager-alarm {
    base alarm-type;
    description
      "Base type for all alarms related to the device manager
       This is never reported, sub-identities for the specific
       device alarms are used in the alarms.";
  }

  identity alarm-type {
    description
      "Base identity for alarm types.  A unique identification of the
       fault, not including the managed object.  Alarm types are used
       to identify if alarms indicate the same problem or not, for
       lookup into external alarm documentation, etc.  Different
       managed object types and instances can share alarm types.  If
       the same managed object reports the same alarm type, it is to
       be considered to be the same alarm.  The alarm type is a
       simplification of the different X.733 and 3GPP alarm IRP alarm
       correlation mechanisms and it allows for hierarchical
       extensions.

       A 'specific-problem' can be used in addition to the alarm type
       in order to have different alarm types based on information not
       known at design-time, such as values in textual SNMP
       Notification varbinds.";
  }
}
