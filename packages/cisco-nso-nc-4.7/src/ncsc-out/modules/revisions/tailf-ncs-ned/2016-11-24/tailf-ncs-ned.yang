module tailf-ncs-ned {
  // Generated by yanger -t ncs
  tailf:mount-id "cisco-nso-nc-4.7:cisco-nso-nc-4.7";
  tailf:ncs-device-type "netconf";

  namespace "http://tail-f.com/ns/ncs-ned";
  prefix ned;

  import tailf-common {
    prefix tailf;
  }
  import tailf-ncs-internal-mount {
    prefix ncs;
  }

  organization
    "Tail-f Systems";
  description
    "This module defines the Tail-f NCS NED base identities.";

  revision 2016-11-24 {
    description
      "Released as part of NCS-4.3.

       Added base identity for NETCONF devices.
       Added identity lsa-netconf";
  }
  revision 2011-06-01 {
    description
      "Released as part of NCS-1.6.";
  }

  identity lsa-netconf {
    base netconf-ned-id;
  }

  identity netconf {
    base netconf-ned-id;
  }

  identity cli-ned-id;

  identity generic-ned-id;

  identity netconf-ned-id;
}
