submodule tailf-ncs-compliance {

  belongs-to tailf-ncs {
    prefix ncs;
  }

  import tailf-common {
    prefix tailf;
  }

  import ietf-yang-types {
    prefix yang;
  }
  import ietf-inet-types {
    prefix inet;
  }

  include tailf-ncs-devices;

  organization "Tail-f Systems";

  description
    "This submodule defines the compliance reporting functions
     of NCS.";

  revision 2016-05-26 {
    description
      "Released as part of NCS-4.2.

       Added /compliance/reports/report/service-checks/historic-changes.
       to be able to report changes from a certain commit interval";
  }

  revision 2013-11-12 {
    description
      "Released as part of NCS-3.0";
  }

  typedef compliance-status-result {
    type enumeration {
      enum no-violation;
      enum violations;
    }
  }

  container compliance {
    description
      "Compliance report management";

    tailf:info "Compliance reporting";
    container reports {
      description
        "Compliance report definitions";
      list report {
        description
          "Compliance report definition";

        key "name";
        leaf name {
          description
            "The name of a report definition";
          type string;
          tailf:info "Compliance report name";
        }
        tailf:action run {
          description
            "Run this compliance report definition and store the report output
             in a file under the state/compliance-reports directory";

          tailf:info "Run this compliance report";
          tailf:actionpoint ncsinternal {
            tailf:internal;
          }
          input {
            leaf title {
              description
                "The title in this report output file";
                tailf:info "Report name + title in report header";
              type string;
            }
            leaf from {
              description
                "The date and time for the lower time boundary in historical
                analysis";
              tailf:info "Audit log and check-sync events from this time";
              type yang:date-and-time;
            }
            leaf to {
              description
                "The date and time for the upper time boundary in historical
                analysis";
              tailf:info "Audit log and check-sync events from this time";
              type yang:date-and-time;
            }
            leaf outformat {
              description
                "The format of this report output file, and therefore also
                 the file suffix";
              type enumeration {
                enum text;
                enum xml;
                enum html;
              }
            }
          }
          output {
            leaf compliance-status {
              description
                "Status indicating if any integrity violations has been
                 discovered on any device or service in this report run";

              tailf:info "Any compliance violations found?";
              type compliance-status-result;
              mandatory true;
            }
            leaf id {
              description
                "The report output file id which is key in the operational
                 data report list /compliance/report-results/report/";
              tailf:info "report file id";
              type uint32;
              mandatory true;
            }
            leaf info {
              description
                "Short description on how many devices and services where
                 covered in this report run";
              type string;
              mandatory true;
            }
            leaf location {
              description
                "URL location for accessing the report output file";
              tailf:info "File location for output";
              type inet:uri;
              mandatory true;
            }
          }
        }
        grouping devices-g {
          choice device-choice {
            mandatory true;
            case all-devices {
              leaf all-devices {
                description
                  "Define all available devices as target for this report";
                tailf:info
                  "Report on all devices";
                type empty;
              }
            }
            case some-devices {
              leaf-list device-group {
                description
                  "Define one or many device groups as target for this report";
                tailf:info "Report on specific device groups";
                type leafref {
                  path "/ncs:devices/device-group/name";
                }
              }
              leaf select-devices {
                description
                  "Let the result of this XPATH expression define devices that
                   is target for this report";
                tailf:info
                  "Report on devices selected by an XPath expression";
                type yang:xpath1.0;
              }
              leaf-list device {
                description
                  "Define one or many devices as target for this report";
                tailf:info "Report on specific devices";
                type leafref {
                  path "/ncs:devices/device/name";
                }
              }
            }
          }
        }
        container device-check {
          presence true;
          description
            "Define the targeted devices for this compliance report definition
             and which verifications that should be performed on
             these devices";
          tailf:info "Report on devices";
          uses devices-g;
          leaf current-out-of-sync {
            description
              "Should a device check-sync be performed and the result added
               to the compliance report, the default is true";
            tailf:info "Should current check-sync action be performed?";
            type boolean;
            default true;
          }
          leaf historic-changes {
            description
              "Should the commit log for the defined time interval (from, to)
               be analysed and device changes added
               to the compliance report, the default is true";
            tailf:info
              "Include commit log events from within
               the report interval";
            type boolean;
            default true;
          }
          leaf historic-out-of-sync {
            description
              "Should logs be scanned for failing device check-sync events
               for the defined time interval (from, to)
               and found events added to the compliance report,
               the default is true";
            tailf:info
              "Include detected devices out of sync events from within
               the report interval";
            type boolean;
            default true;
          }
        }
        container service-check {
          presence true;
          description
            "Define the targeted services for this compliance report definition
             and which verifications that should be performed on
             these services";
          tailf:info "Report on services out of sync";
          choice service-choice {
            mandatory true;
            case all-services {
              leaf all-services {
                description
                  "Define all available services as target for this report";
                tailf:info
                  "Report on all services";
                type empty;
              }
            }
            case some-services {
              leaf select-services {
                description
                  "Let the result of this XPATH expression define services that
                   is target for this report";
                tailf:info
                  "Report on services selected by an XPath expression";
                type yang:xpath1.0;
              }
              leaf-list service {
                description
                  "Define one or many services as target for this report";
                tailf:info
                  "Report on specific services";
                type instance-identifier;
              }
            }
          }
          leaf current-out-of-sync {
            description
              "Should a service check-sync be performed and the result added
               to the compliance report, the default is true";
            tailf:info "Should current check-sync action be performed?";
            type boolean;
            default true;
          }
          leaf historic-changes {
            description
              "Should the commit log for the defined time interval (from, to)
               be analysed and service changes added
               to the compliance report, the default is true";
            tailf:info
              "Include commit log events from within
               the report interval";
            type boolean;
            default true;
          }
          leaf historic-out-of-sync {
            description
              "Should logs be scanned for failing service check-sync events
               for the defined time interval (from, to)
               and found events added to the compliance report,
               the default is true";
            tailf:info
              "Include detected services out of sync events from within
               the report interval";
            type boolean;
            default true;
          }
        }
        list compare-template {
          description
           "Define device templates that is used to verify current
            configuration against. If devices differ the resulting diff
            is added to the compliance report";
          tailf:info "Diff devices against templates";
          key "template-name device-group";
          leaf template-name {
            description
              "Template name from /devices/template";
            tailf:info "Diff this template";
            type leafref {
              path "/ncs:devices/ncs:template/ncs:name";
            }
          }
          leaf device-group {
            description
              "Device group to apply the template on";
            tailf:info "Report on specific device groups";
            type leafref {
              path "/ncs:devices/device-group/name";
            }
          }
          list variable {
            description
              "Set of variables to be substituted in the template";
            tailf:info "Variables passed to the template";
            key name;
            leaf name {
              description
                "Variable name from the template definition";
              tailf:info "Variable name in template";
              type string;
            }
            leaf value {
              description
                "Value for the variable";
              tailf:info "Value for the variable";
              type string;
            }
          }
        }
      }
    }

    container report-results {
      description
        "Operational data view of compliance report output files";
      config false;
      tailf:callpoint ncs {
        tailf:internal;
      }
      list report {
        key id;
        leaf id {
          description
            "Report output file Id";
          tailf:cli-allow-range;
          type uint32;
        }
        leaf name {
          description
            "Report definition in /compliance/reports/report as basis
             for this report output file";
          type string;
          tailf:non-strict-leafref {
            path "/compliance/reports/report/name";
          }
        }
        leaf title {
          description
            "The title in this report output file";
          type string;
        }
        leaf time {
          description
            "The Date and time when this report output file was produced";
          type yang:date-and-time;
        }
        leaf who {
          description
            "The name of the producer of this report output file";
          tailf:info "User that ran the report";
          type string;
        }
        leaf compliance-status {
          description
            "Status indicating if any integrity violations has been
             discovered on any device or service in this report run";
          tailf:info "Any discrepancies found";
          type compliance-status-result;
        }
        leaf location {
          description
            "URL location for accessing the report output file";
          tailf:info "Location and name of generated report";
          type inet:uri;
        }

        tailf:action remove {
          description
            "Remove this report result.";
          tailf:info "Remove this report result";
          tailf:actionpoint ncsinternal {
            tailf:internal;
          }
        }
      }
    }
  }
}
