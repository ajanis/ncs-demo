module tailf-ned-alu-sr {
  // Generated by yanger -t ncs
  tailf:mount-id "alu-sr-cli-3.4:alu-sr-cli-3.4";
  tailf:ncs-device-type "cli-ned";

  namespace "http://tail-f.com/ned/alu-sr";
  prefix alu;

  import tailf-common {
    prefix tailf;
  }
  import ietf-inet-types {
    prefix inet;
  }
  import tailf-ncs {
    prefix ncs;
  }

  revision 2015-06-11 {
    description
      "3.4
       New release.
       Enhancements:
       Corrections:
        Use explicit-exit annotation in / router * / policy-options
        Major YANG model change. Most shutdown leafs now modelled as booleans
        with default values.
      ";
  }
  revision 2015-06-01 {
    description
      "3.2.6.1
       Enhancements:
       Corrections:
        Make the NED calculate transid evel when it is connected to a netsim
        device.
      ";
  }
  revision 2015-05-29 {
    description
      "3.2.6
       New release.
       Enhancements:
       Corrections:
        Fixed a dependency issue in / port *
      ";
  }
  revision 2015-05-28 {
    description
      "3.2.4.12
       Enhancements:
         Added set hooks at the locations below to mimic the behavior of the
         device;
          / router * / mpls
          / qos / network-queue *
         Additions to the YANG model in
         / router * / bgp / group * / neighbor * /
         / router * / bgp / group * /
         / router * / ldp
         / router *
       Corrections:
         / router * / rsvp repends on / router * / mpls
         Fixed misspelled leaf 'local-preferences' to 'local-preference'
         Use flat-list-syntax on all leaf-lists
         Fixed dependency issue with
         / router * / interface * / port

      ";
  }
  revision 2015-05-25 {
    description
      "3.2.4.11
       Enhancements:
       Added // qos / sap-ingress * / queue * / adaption-rule
       Corrections:
       Added tailf:dependency to // cflowd / cache-size / collector * /
        template-set
      ";
  }
  revision 2015-05-25 {
    description
      "3.2.4.10
       Enhancements:
       Added
        / system / security / tacplus *
        / router * / bgp / group * / neighbor * / peer-as
       Corrections:
       Fixed YANG model bugs in
       / router * / policy-options / begin / policy-statement * / default-action
       / system / security / source-address
       / system / security / snmp
      ";
  }
  revision 2015-05-21 {
    description
      "3.2.4.9
       Enhancements:
        The NED is now automatically storing information about OS version
        and machine model in / devices / device * / platform
        Added:
          // qos / fabric-profile
          // card * / mda * / access / ingress / fabric-policy
          // card * / mda * / network / ingress / fabric-policy
          // ip-address-range
          // card * / mda * / network / ingress / pool
          // cflowd /
          // ipsec /
          // isa /
          // port * / ethernet / ingress-rate
          // port * / modify-buffer-allocation-rate /
          // port * / network /
          // port * / tdm / ds1 * / clock-source
          // port * / tdm / ds3 * / clock-source
          // qos / sap-ingress * / prec
          // qos / sap-ingress * / queue * / adaption-rule
          // qos / sap-ingress * / default-priority
          // qos / sap-ingress * / queue * / adaption-rule
          // qos / slope-policy * / description
          // log / accounting-policy * /
          // service / ies * / interface * / tos-marking-state
          // service / vpls * / sap * / restrict-protected-src
          // service / vpls * / bgp-vpls
          // service / vprn * / dhcp
          // service / vprn * / dhcp / local-dhcp-server *
          // service / vprn * / ipsec
          // service / vprn * / bgp / damping
          // service / vprn * / interface * / sap * / collect-stats
          // service / vprn * / interface * / sap * / ipsec-tunnel
          // service / vprn * / spoke-sdp *
          // service / vprn * / static-route * ipsec-tunnel
          // service / vprn * / pim / rp / static / address *
          // service / vprn * / mvpn / provider-tunnel / inclusive / pim
          // service / pw-template * / use-provisioned-sdp
          // router * / ospf3
          // router * / mpls / resignal-timer
          // router * / mpls / srlg-frr
          // router * / policy-options
          // router * / pim / rp / static / address *
          // router * / pim / rp / bsr-candidate
          // router * / pim / rp / rp-candidate
          // test-oam /
          // mirror / mirror-dest * type
          // saa /

       Corrections:
        In / service / pw-template *
        Use flat-list-syntax in
        / router * / bgp / group * / family
      ";
  }
  revision 2015-05-11 {
    description
      "3.2.4.8
       Enhancements:
        Additions to
         / router * / pim /
         / router * / pim / interface *
         / filter / ipv6-filter * / entry * / match / next-header
         / service / ies * / interface * / sap * / egress / filter
         / service / ies * / interface * / sap * / ingress / filter
       Corrections:
      ";
  }
  revision 2015-05-04 {
    description
      "3.2.4.7
       Enhancements:
        Additions to
         / service / vprn * / dhcp
         / service / vprn * / ipsec
       Corrections:
        Added dependency on
         / service vpls * / sap * / multi-service-site
      ";
  }
  revision 2015-04-23 {
    description
      "3.2.4.6
       Enhancements:
        Added new config under
         / service / vprn * / ipsec
         / service / vprn * / dhcp
       Corrections:
        Changed model for most of the shutdown leaf. Now modelled as boolean
        with a default value. Previously modelled as empty with a cli-show-no
        annotation.
      ";
  }
  revision 2015-04-09 {
    description
      "3.2.4.5
       Enhancements:
       Corrections:
        Added more SAP dependencies. A SAP entry is unique througout the
        system. I.e a SAP id can only exist once in either the vpls, ies,
        vprn or epipe lists.
      ";
  }
  revision 2015-04-08 {
    description
      "3.2.4.4
       Enhancements:
        Added / service / vpls * / interface *
       Corrections:
      ";
  }
  revision 2015-04-02 {
    description
      "3.2.4.3
       Enhancements:
       Corrections:
         Solved dependency issue between:
           / router * / ospf * / area * / interface
         and
           / router * / interface
         Added dependency between:
           / router * / interface
         and
           / port * /
         Added non-strict-leafref on:
           / router * / interface * / qos
      ";
  }
  revision 2015-03-19 {
    description
      "3.2.4.2
       Enhancements:
       Corrections:
         Changed the following leafs to enumerations:
         / port * / ethernet / mode
         / port * / ethenet / encap-type
         Added dependency between:
         / port * / ethernet / network and / port * / ethernet / mode
         The following leaf is now a non-strict leafref:
         / port * / ethernet / network / queue-policy
      ";
  }
  revision 2015-03-11 {
    description
      "3.2.2.3
       Verified with NCS-3.4
       Enhancements:
       Corrections:
       Changed order of
       / port * / ethernet / mode and / port * / ethernet / encap-type
      ";
  }
  revision 2015-03-05 {
    description
      "3.2.2.2
       Enhancements:
       New elements added under
       / port * / ethernet
       / qos / port-scheduler-policy
       / qos / policer-control-policy
       / router * / mpls / static-lsp
       Corrections:
       Changed to a non strict leafreaf at the following location
       / service / sdp * / lsp
      ";
  }
  revision 2015-03-03 {
    description
      "3.2.2.1
       Enhancements:
       New elements added under / router * / ospf *
       Corrections:
       Changed the key for the / router * / ospf * list to be compliant with
       the device. An ospf instance id is used instead of previously the ospf
       router id.
      ";
  }
  revision 2015-02-20 {
    description
      "3.2.2
       Enhancements:
       Corrections:
       Minor fixes done at the following after testing with a real device:
        / sap  * / egress / scheduler-policy
        / port * / shutdown
        / service / customer * / multi-service-site
        / service / ies * / interface * / ipv6 dhcp6-relay / shutdown
        / service / vpls * / sap * / egress
        / service / vpls * / bgp-ad
        / system /  time / sntp / shutdown
        / router * / interface * / port
      ";
  }
  revision 2015-02-18 {
    description
      "3.2.1.9
       Enhancements:
        Addition in
        // service / vprn * / interface * / ipv6
        // service / vprn * / router-id
        // service / vprn * / isis *
        // router * / pim /
        // system / security / profile / entry *
       Corrections:
      ";
  }
  revision 2015-02-17 {
    description
      "3.2.1.8
       Enhancements:
        Addition in
        / service / vpls * / pim-snooping
        / service / vpls * / spoke-sdp * split-horizon-group
        / service / vprn * / bgp / authentication-key
        / service / vprn * / bgp / group * /
        / service / vprn * / interface * /
       Corrections:
      ";
  }
  revision 2015-02-12 {
    description
      "3.2.1.7
       Enhancements:
       Additions in
        / sap  * / egress / qinq-mark-top-only
        / card  * / network
        / port * / ethernet / lldp
        / port / ethernet / network
        / qos / network-queue * / queue * / port-parent
        / qos / sap-egress * / fc * / burst-limit
        / qos / slope-policy *
        / qos / port-scheduler-policy *
        / eth-cfm / domain * / name
        / log / file-id * / description
        / log / log-id * / to
        / log / syslog * / level
        / service / vpls * / allow-ip-int-binding
        / service / vpls * / service-name
        / service / vpls * / bgp
        / service / vpls * / bgp-ad
        / service / vprn * / interface * / secondary
        / service / vprn * / interface * / vpls *
        / service / vprn * / static-route *
        / service / vprn * / sgt-qos
        / service / vprn * / pim
        / service / vprn * / mvpn
        / service / pw-template *
        / router * / ospf / area * / interface
        / router * / ospf
        / router * / mpls / lsp-template *
        / router * / ldp / interface-parameters
        / router * / rsvp /   authentication-key
        / router * / interface * / bfd
        / router * / policy-options / as-path
        / router * / pim
        / system / chassis-mode * / power-supply *
        / system / security
        / filter / mac-filter * / entry *
      ";
  }
  revision 2015-02-10 {
    description
      "3.2.1.6
       Enhancements:
        Extended the proxy server connection setup with support for serial
        terminal servers.

        Added support for running some native commands as actions through the
        device live-status in the NCS CLI.
       Corrections:
        Added diff-dependency between / router * / router-advertisement
        and / service / ies *
        Added diff-dependency between / router * / mld and / service / ies *
      ";
  }
  revision 2015-01-13 {
    description
      "3.2.1.4
       Enhancements:

       Corrections:
        Using real leafref instead of non-strict-leafref on:
         / service / vpls * / sap  * / multi-service-site
         / service / epipe * / sap  * / multi-service-site
         / service / ies * / sap  * / multi-service-site
      ";
  }
  revision 2015-01-12 {
    description
      "3.2.1.3
       Enhancements:

       Corrections:
        Added appropriate leafref dependencies
          towards:
          / service / customer * / multi-service-site
          for:
          / service / vpls * / sap  * / multi-service-site
          / service / epipe * / sap  * / multi-service-site
          / service / ies * / sap  * / multi-service-site
        Added appropriate trigger-on-set dependencies between:
          / service / vpls * / sap * / multi-service-site
          and
          / service / vpls * / sap * / egress / schedule-policy
        ";
  }
  revision 2014-12-19 {
    description
      "3.2.1.2
       Enhancements:

       Corrections:
       Changed the order of scheduler-policy and scheduler-override at the
       following locations:
        / service / customer * / multi-service-site * / ingress
        / service / customer * / multi-service-site * / egress
       Removed create leaf from:
        / router * / mld / interface *
      ";
  }
  revision 2014-12-02 {
    description
      "3.2.1.1
       Enhancements:

       Corrections:
       added missing cli-no-value-on-delete on the following leaf:
        / service / customer * / multi-service-site * / egress / scheduler-polic
      ";
  }
  revision 2014-11-26 {
    description
      "3.2.1
       New release
      ";
  }
  revision 2014-11-24 {
    description
      "3.2.0.2
       Enhancements:
       NED config parameters in tailf-alu-sr-meta.yang are now configurable
       on global, profile and device level,

       Corrections:
      ";
  }
  revision 2014-11-20 {
    description
      "3.2.0.1
       Enhancements:
       More info strings
       Additions in / port / ethernet / hold-time
       Additions in / port * / dwdm /
       Additions in / port * / otu
       Additions in / router *
       Additions in / router * / isis * / level
       Additions in / system / rollback
       Additions in / system / time / ntp

       Corrections:
       Added missing cli-add-mode in / port * / dwdm / coherent
       Added missing cli-add-mode in / system / ethernet
       Added support for ipv6 in / service / vprn * / bgp / group * / neighbor
       Fixed annotation issue with / service / customer * / multi-service-site
        * / ingress / rate
       Fixed annotation issue with / service / customer * / multi-service-site
        * / egress / rate
      ";
  }
  revision 2014-11-18 {
    description
      "3.2
       Prepared for release";
  }
  revision 2014-11-10 {
    description
      "3.1.0.7
       Added tailf:cli-explicit-exit to router * / policy-options
       Changed / router * / isis. Is now a list.
       Added new functionality in / router / isis * /
       Added new functionality in / service / ies * / ipv6 / dhcp6-relay
       Added new functionality in / service / ies * / interface *
       Added basic support for / log
       Added support for / router * / bgp
       Added support for / router * / router-advertisement
       Added missing annotation in / router * / interface * / port.
       Added missing annotation in lag * / lacp.
       Changed filter / ip-filter * / embed-filter to a non-strict-leafref";
  }
  revision 2014-11-07 {
    description
      "3.1.0.6
       added missing cli-no-value-on-delete on the following leaf:
       service / customer * / multi-service-site * / ingress / scheduler-polic";
  }
  revision 2014-11-03 {
    description
      "3.1.0.5
       Added support for configurable behaviour upon admin-save failure.
       This feauture is modelled in the tailf-alu-sr-meta.yang";
  }
  revision 2014-10-31 {
    description
      "3.1.0.4
       Added support for / qos / queue-group-templates
       Added support for / service / vpls * / mesh-sdp * / ingress / qos";
  }
  revision 2014-10-09 {
    description
      "3.1.0.2
       Leaf /service / vpls * / mesh-sdb * / def-mesh-vc-id must have its
       value present when deleted and can only be deleted after mesh-sdp";
  }
  revision 2014-10-03 {
    description
      "3.1.0.1
        Fixed a sequence issue in filter / ip-filter * / match / dst-port
        Fixed a sequence issue with filter / ip-filter * / match / src-port";
  }
  revision 2014-09-11 {
    description
      "3.1
       Added missing annotation in / router * / interface * / port.
       Added missing annotation in lag * / lacp.
        Changed filter / ip-filter * / embed-filter to a non-strict-leafref";
  }
  revision 2014-09-05 {
    description
      "3.0.2.0
       Using new tail:cli-diff-dependency extension to solve creation order
       of SAP objects in different subtrees.";
  }
  revision 2014-08-20 {
    description
      "3.0.1.1
       Added support for router * / policy-options
       Added more complete support for service / vprn *";
  }
  revision 2014-08-13 {
    description
      "Various minor fixes to the system / security / cpm-filter subtree";
  }
  revision 2014-08-11 {
    description
      "Various minor fixes in system, redundancy and filter subtrees";
  }
  revision 2014-07-03 {
    description
      "Changed modelling of the shutdown leafs. They are now modelled as type
       empty and with tailf:cli-show-no extension. Done to get rid of
       out-of-sync issues caused by the ALU device when it automatically
       displays shutdown/no shutdown even when it has not explicitly been set
      ";
  }
  revision 2014-06-11 {
    description
      "Added support for new config specific for ALU 7210 devices";
  }
  revision 2014-06-08 {
    description
      " Added support for
        - vpls * / sap * / auto-learn-mac-protect
        - vpls * / sap * / restrict-protected-src
        - vpls * / mesh-sdp * / auto-learn-mac-protect
        - vpls * / mesh-sdp * / restrict-protected-src";
  }
  revision 2014-06-05 {
    description
      "- Replaced all ipv6-with-prefix with ipv6-address-and-prefix-length
       - All description leaf now tagged with tailf:cli-no-value-on-delete";
  }
  revision 2014-05-23 {
    description
      "- Added support for debug/mirror-source configurations
       - Added support for mirror/mirror-destination configurations
       - Disabled the scope-leaf under filter/ip-filter and filter/ipv6-filter
        The reason is that this leaf is not displayed properly when the ALU
        device dumps the configurations. This results in out-of-sync issues
       - Moved ip-filter-entry to a grouping used by all nodes implementing
        filter entries.
       - Added support for service/ies/interface/sap/ingress/queue-override
       - Added support for service/ies/interface/sap/egress/queue-override
       - Fixed minor issues in qos/scheduler-policy
       - Added qos/sap-egress/ip-criteria
       - Added qos/sap-egress/ipv6-criteria
       - Changed type ipv4-prefix to tailf:ipv4-address-and-prefix-length
       - Changed type ipv6-prefix to tailf:ipv6-address-and-prefix-length
       - Fixed bug in service/ies/interface/ipv6/dhcp6-relay/shutdown
       - Fixed leafref in router * / . All subtrees with interface leaf shall
        refer to router/interface.
       - Implemented router/ldp/targeted-session/peer";
  }
  revision 2014-04-28 {
    description
      "- Added support for service/vpls configurations
       - Fixed issues related to acl on filter/ip-filter
         and filter/ipv6-filter.
       - SAP id is now a plain string in order to support all the
         ~20 different id formats.
       - Added comments to make the yang code easier to navigate.
       - Added limited support for service/vprn configurations.
       - Added limited support for router/ospf configurations.
       - Added limited support for router/mpls configurations.
       - Added limited support for router/l2tp configurations.
       - Added limited support for router/ldp configurations.
       - Added an action <native-cmd> that allows sending strings
         containing native commands directly to the target.";
  }
  revision 2014-01-31 {
    description
      "Added support for filter ip-filter";
  }

  typedef ncs_template_dscp-type {
    type string;
  }

  typedef ncs_template_vpls-id {
    type string;
  }

  typedef ncs_template_ieee-mac {
    type string;
  }

  typedef ncs_template_direction {
    type string;
  }

  typedef ncs_template_test-pattern {
    type string;
  }

  typedef ncs_template_limit-mac-move {
    type string;
  }

  typedef ncs_template_filter-action {
    type string;
  }

  typedef ncs_template_adaption-rule {
    type string;
  }

  typedef ncs_template_protocol {
    type string;
  }

  typedef ncs_template_icmp-type {
    type string;
  }

  typedef ncs_template_icmpv6-type {
    type string;
  }

  typedef ncs_rpc_notif_dscp-type {
    type enumeration {
      enum "be";
      enum "ef";
      enum "cp1";
      enum "cp2";
      enum "cp3";
      enum "cp4";
      enum "cp5";
      enum "cp6";
      enum "cp7";
      enum "cp9";
      enum "cs1";
      enum "cs2";
      enum "cs3";
      enum "cs4";
      enum "cs5";
      enum "nc1";
      enum "nc2";
      enum "af11";
      enum "af12";
      enum "af13";
      enum "af21";
      enum "af22";
      enum "af23";
      enum "af31";
      enum "af32";
      enum "af33";
      enum "af41";
      enum "af42";
      enum "af43";
      enum "cp11";
      enum "cp13";
      enum "cp15";
      enum "cp17";
      enum "cp19";
      enum "cp21";
      enum "cp23";
      enum "cp25";
      enum "cp27";
      enum "cp29";
      enum "cp31";
      enum "cp33";
      enum "cp35";
      enum "cp37";
      enum "cp39";
      enum "cp41";
      enum "cp42";
      enum "cp43";
      enum "cp44";
      enum "cp45";
      enum "cp47";
      enum "cp49";
      enum "cp50";
      enum "cp51";
      enum "cp52";
      enum "cp53";
      enum "cp54";
      enum "cp55";
      enum "cp57";
      enum "cp58";
      enum "cp59";
      enum "cp60";
      enum "cp61";
      enum "cp62";
      enum "cp63";
    }
  }

  typedef ncs_rpc_notif_vpls-id {
    type union {
      type string {
        length "1..64";
        tailf:info
          "<string id>;; max length 64";
      }
      type uint32 {
        range "1..2147483647";
        tailf:info
          "<numeric id>;;[1..2147483647]";
      }
    }
  }

  typedef ncs_rpc_notif_ieee-mac {
    tailf:info
      "<ieee mac address>;; xx:xx:xx:xx:xx:xx or xx-xx-xx-xx-xx-xx";
    type string;
  }

  typedef ncs_rpc_notif_direction {
    tailf:info
      "<direction>;; up | down";
    type enumeration {
      enum "up";
      enum "down";
    }
  }

  typedef ncs_rpc_notif_test-pattern {
    type enumeration {
      enum "all-zeros";
      enum "all-ones";
    }
  }

  typedef ncs_rpc_notif_limit-mac-move {
    type enumeration {
      enum "blockable";
      enum "non-blockable";
    }
  }

  typedef ncs_rpc_notif_filter-action {
    type enumeration {
      enum "permit";
      enum "deny";
      enum "deny-host-unreachable";
    }
  }

  typedef ncs_rpc_notif_adaption-rule {
    type enumeration {
      enum "max";
      enum "min";
      enum "closest";
    }
  }

  typedef ncs_rpc_notif_protocol {
    type union {
      type enumeration {
        enum "none";
        enum "crtp";
        enum "crudp";
        enum "egp";
        enum "eigrp";
        enum "encap";
        enum "ether-ip";
        enum "gre";
        enum "icmp";
        enum "idrp";
        enum "igmp";
        enum "igp";
        enum "ip";
        enum "ipv6";
        enum "ipv6-frag";
        enum "ipv6-icmp";
        enum "ipv6-no-nxt";
        enum "ipv6-opts";
        enum "ipv6-route";
        enum "isis";
        enum "iso-ip";
        enum "l2tp";
        enum "ospf-igp";
        enum "pim";
        enum "pnni";
        enum "ptp";
        enum "rdp";
        enum "rsvp";
        enum "stp";
        enum "tcp";
        enum "udp";
        enum "vrrp";
        enum "*";
      }
      type uint8 {
        range "1..255";
      }
      type string;
    }
  }

  typedef ncs_rpc_notif_icmp-type {
    type union {
      type uint8;
      type enumeration {
        enum "none";
        enum "echo-reply";
        enum "dest-unreachable";
        enum "source-quench";
        enum "redirect";
        enum "echo-request";
        enum "router-advt";
        enum "router-selection";
        enum "time-exceeded";
        enum "parameter-problem";
        enum "timestamp-request";
        enum "timestamp-reply";
        enum "addr-mask-request";
        enum "addr-mask-reply";
      }
    }
  }

  typedef ncs_rpc_notif_icmpv6-type {
    type union {
      type uint8;
      type enumeration {
        enum "redirect";
        enum "packet-too-big";
        enum "redirect-message";
        enum "echo-reply";
        enum "echo-request";
        enum "time-exceeded";
        enum "dest-unreachable";
        enum "router-advt";
        enum "router-solicitation";
        enum "neighbor-solicitation";
        enum "neighbor-advertisement";
        enum "multicast-listen-report";
        enum "multicast-listen-done";
      }
    }
  }

  typedef dscp-type {
    type enumeration {
      enum "be";
      enum "ef";
      enum "cp1";
      enum "cp2";
      enum "cp3";
      enum "cp4";
      enum "cp5";
      enum "cp6";
      enum "cp7";
      enum "cp9";
      enum "cs1";
      enum "cs2";
      enum "cs3";
      enum "cs4";
      enum "cs5";
      enum "nc1";
      enum "nc2";
      enum "af11";
      enum "af12";
      enum "af13";
      enum "af21";
      enum "af22";
      enum "af23";
      enum "af31";
      enum "af32";
      enum "af33";
      enum "af41";
      enum "af42";
      enum "af43";
      enum "cp11";
      enum "cp13";
      enum "cp15";
      enum "cp17";
      enum "cp19";
      enum "cp21";
      enum "cp23";
      enum "cp25";
      enum "cp27";
      enum "cp29";
      enum "cp31";
      enum "cp33";
      enum "cp35";
      enum "cp37";
      enum "cp39";
      enum "cp41";
      enum "cp42";
      enum "cp43";
      enum "cp44";
      enum "cp45";
      enum "cp47";
      enum "cp49";
      enum "cp50";
      enum "cp51";
      enum "cp52";
      enum "cp53";
      enum "cp54";
      enum "cp55";
      enum "cp57";
      enum "cp58";
      enum "cp59";
      enum "cp60";
      enum "cp61";
      enum "cp62";
      enum "cp63";
    }
  }

  typedef vpls-id {
    type union {
      type string {
        length "1..64";
        tailf:info
          "<string id>;; max length 64";
      }
      type uint32 {
        range "1..2147483647";
        tailf:info
          "<numeric id>;;[1..2147483647]";
      }
    }
  }

  typedef ieee-mac {
    tailf:info
      "<ieee mac address>;; xx:xx:xx:xx:xx:xx or xx-xx-xx-xx-xx-xx";
    type string;
  }

  typedef direction {
    tailf:info
      "<direction>;; up | down";
    type enumeration {
      enum "up";
      enum "down";
    }
  }

  typedef test-pattern {
    type enumeration {
      enum "all-zeros";
      enum "all-ones";
    }
  }

  typedef limit-mac-move {
    type enumeration {
      enum "blockable";
      enum "non-blockable";
    }
  }

  typedef filter-action {
    type enumeration {
      enum "permit";
      enum "deny";
      enum "deny-host-unreachable";
    }
  }

  typedef adaption-rule {
    type enumeration {
      enum "max";
      enum "min";
      enum "closest";
    }
  }

  typedef protocol {
    type union {
      type enumeration {
        enum "none";
        enum "crtp";
        enum "crudp";
        enum "egp";
        enum "eigrp";
        enum "encap";
        enum "ether-ip";
        enum "gre";
        enum "icmp";
        enum "idrp";
        enum "igmp";
        enum "igp";
        enum "ip";
        enum "ipv6";
        enum "ipv6-frag";
        enum "ipv6-icmp";
        enum "ipv6-no-nxt";
        enum "ipv6-opts";
        enum "ipv6-route";
        enum "isis";
        enum "iso-ip";
        enum "l2tp";
        enum "ospf-igp";
        enum "pim";
        enum "pnni";
        enum "ptp";
        enum "rdp";
        enum "rsvp";
        enum "stp";
        enum "tcp";
        enum "udp";
        enum "vrrp";
        enum "*";
      }
      type uint8 {
        range "1..255";
      }
      type string;
    }
  }

  typedef icmp-type {
    type union {
      type uint8;
      type enumeration {
        enum "none";
        enum "echo-reply";
        enum "dest-unreachable";
        enum "source-quench";
        enum "redirect";
        enum "echo-request";
        enum "router-advt";
        enum "router-selection";
        enum "time-exceeded";
        enum "parameter-problem";
        enum "timestamp-request";
        enum "timestamp-reply";
        enum "addr-mask-request";
        enum "addr-mask-reply";
      }
    }
  }

  typedef icmpv6-type {
    type union {
      type uint8;
      type enumeration {
        enum "redirect";
        enum "packet-too-big";
        enum "redirect-message";
        enum "echo-reply";
        enum "echo-request";
        enum "time-exceeded";
        enum "dest-unreachable";
        enum "router-advt";
        enum "router-solicitation";
        enum "neighbor-solicitation";
        enum "neighbor-advertisement";
        enum "multicast-listen-report";
        enum "multicast-listen-done";
      }
    }
  }

  grouping ncs_template_src-dst-ip {
    leaf src-ip {
      type string;
    }
    leaf dst-ip {
      type string;
    }
  }

  grouping ncs_template_ip-address-range {
    list low-high-list {
      // NCS patched for predictable order
      ordered-by user;
      key "low high";
      leaf low {
        type string;
      }
      leaf high {
        type string;
      }
    }
  }

  grouping ncs_template_eth-cfm {
    list mep {
      // NCS patched for predictable order
      ordered-by user;
      key "mep-id";
      leaf mep-id {
        // NCS drop mandatory statement
        type string;
      }
      leaf domain {
        type string;
        // NCS drop mandatory statement
      }
      leaf association {
        type string;
        // NCS drop mandatory statement
      }
      leaf direction {
        type ncs_template_direction;
      }
      container ais-enable {
        leaf-list client-meg-level {
          // NCS patched for predictable order
          ordered-by user;
          type string;
        }
        leaf description {
          type string;
        }
        leaf interval {
          type string;
        }
        leaf priority {
          type string;
        }
      }
      leaf ccm-enable {
        type empty;
      }
      leaf ccm-ltm-priority {
        type string;
      }
      leaf ccm-padding-size {
        type string;
      }
      leaf description {
        type string;
      }
      container eth-test-enable {
        uses ncs_template_eth-test;
      }
      leaf fault-propagation-enable {
        type string;
      }
      leaf low-priority-defect {
        type string;
      }
      leaf mac-address {
        type ncs_template_ieee-mac;
      }
      leaf one-way-delay-threshold {
        type string;
      }
      leaf shutdown {
        // NCS drop default statement
        type string;
      }
    }
  }

  grouping ncs_template_igmp-snooping {
    leaf disable-router-alert {
      type empty;
    }
    leaf fast-leave {
      type empty;
    }
    leaf import {
      type string;
    }
    leaf last-member-query-interval {
      type string;
    }
    leaf max-num-groups {
      type string;
    }
    leaf mrouter-port {
      type empty;
    }
    leaf query-interval {
      type string;
    }
    leaf query-response-interval {
      type string;
    }
    leaf robust-count {
      type string;
    }
    leaf send-queries {
      type empty;
    }
    container static {
      list group {
        // NCS patched for predictable order
        ordered-by user;
        // NCS drop max-elements statement
        key "group-address";
        leaf group-address {
          type string;
        }
        leaf stdarg {
          type string;
        }
      }
    }
    leaf version {
      type string;
    }
  }

  grouping ncs_template_sdp-common {
    leaf sdp-id {
      type string;
    }
    leaf vc-id {
      type string;
    }
    leaf vc-type {
      type string;
    }
    leaf endpoint {
      type string;
    }
    leaf shutdown {
      // NCS drop default statement
      type string;
    }
  }

  grouping ncs_template_sdp-spoke-mesh-common {
    uses ncs_template_sdp-common;
    leaf accounting-policy {
      type string;
    }
    leaf auto-learn-mac-protect {
      type empty;
    }
    leaf collect-stats {
      type empty;
    }
    container egress {
      container filter {
        uses ncs_template_filter-choice;
      }
      container qos {
        leaf network-policy-id {
          type string;
        }
        leaf port-redirect-group {
          type string;
        }
        leaf instance {
          type string;
        }
      }
      leaf vc-label {
        type string;
      }
    }
    container eth-cfm {
      uses ncs_template_eth-cfm;
    }
    leaf force-vlan-forwarding {
      type empty;
    }
    container igmp-snooping {
      uses ncs_template_igmp-snooping;
    }
    container ingress {
      container filter {
        uses ncs_template_filter-choice;
      }
      container qos {
        leaf network-policy-id {
          type string;
        }
        leaf fp-redirect-group {
          type string;
        }
        leaf instance {
          type string;
        }
      }
      leaf vc-label {
        type string;
      }
    }
    leaf mac-pinning {
      type empty;
    }
    list static-mac {
      // NCS patched for predictable order
      ordered-by user;
      key "address";
      leaf address {
        type ncs_template_ieee-mac;
      }
    }
    leaf restrict-protected-src {
      type string;
    }
    leaf vlan-vc-tag {
      type string;
    }
  }

  grouping ncs_template_stp-common {
    leaf auto-edge {
      type empty;
    }
    leaf edge-port {
      type empty;
    }
    leaf link-type {
      type string;
    }
    leaf path-cost {
      type string;
    }
    leaf port-num {
      type string;
    }
    leaf priority {
      type string;
    }
    leaf shutdown {
      // NCS drop default statement
      type string;
    }
  }

  grouping ncs_template_filter-choice {
    choice filter {
      leaf ip {
        type string;
      }
      leaf ipv6 {
        type string;
      }
      leaf mac {
        type string;
      }
    }
  }

  grouping ncs_template_eth-test {
    leaf test-pattern {
      type ncs_template_test-pattern;
    }
    leaf crc-enable {
      type empty;
      // NCS drop when statement
    }
  }

  grouping ncs_template_time-stamp {
    leaf start-week {
      type string;
    }
    leaf start-day {
      type string;
    }
    leaf month {
      type string;
    }
    leaf hours-minutes {
      type string;
    }
  }

  grouping ncs_template_ip-filter-entry-grouping {
    leaf entry-name {
      type string;
    }
    leaf description {
      type string;
    }
    leaf log {
      type string;
    }
    container match {
      leaf protocol {
        type ncs_template_protocol;
      }
      leaf dscp {
        type ncs_template_dscp-type;
      }
      container src-ip {
        uses ncs_template_filter-match-ip-grouping;
      }
      container dst-ip {
        uses ncs_template_filter-match-ip-grouping;
      }
      leaf icmp-type {
        type ncs_template_icmp-type;
      }
      leaf icmp-code {
        type string;
      }
      leaf fragment {
        type string;
      }
      container ip-option {
        leaf a {
          type string;
        }
        leaf b {
          type string;
        }
      }
      container dst-port {
        choice port-choice {
          case a {
            leaf op {
              type string;
            }
            leaf port {
              // NCS drop mandatory statement
              type string;
            }
          }
          case b {
            leaf range {
              type empty;
            }
            leaf start {
              // NCS drop mandatory statement
              type string;
            }
            leaf end {
              // NCS drop mandatory statement
              type string;
            }
          }
        }
      }
      container src-port {
        choice port-choice {
          case a {
            leaf op {
              type string;
            }
            leaf port {
              // NCS drop mandatory statement
              type string;
            }
          }
          case b {
            leaf range {
              type empty;
            }
            leaf start {
              // NCS drop mandatory statement
              type string;
            }
            leaf end {
              // NCS drop mandatory statement
              type string;
            }
          }
          case c {
            leaf src-port-number {
              type string;
            }
            leaf mask {
              // NCS drop mandatory statement
              type string;
            }
          }
        }
      }
    }
  }

  grouping ncs_template_ipv6-filter-entry-grouping {
    leaf entry-name {
      type string;
    }
    leaf description {
      type string;
    }
    container match {
      leaf next-header {
        type string;
      }
      leaf dscp {
        type ncs_template_dscp-type;
      }
      container src-ip {
        uses ncs_template_filter-match-ipv6-grouping;
      }
      container dst-ip {
        uses ncs_template_filter-match-ipv6-grouping;
      }
      leaf icmp-type {
        type ncs_template_icmpv6-type;
      }
      leaf icmp-code {
        type string;
      }
      leaf fragment {
        type string;
      }
      container ip-option {
        leaf a {
          type string;
        }
        leaf b {
          type string;
        }
      }
      container dst-port {
        choice port-choice {
          case a {
            leaf op {
              type string;
            }
            leaf port {
              type string;
            }
          }
          case b {
            leaf range {
              type empty;
            }
            leaf start {
              type string;
            }
            leaf end {
              type string;
            }
          }
        }
      }
      container src-port {
        choice port-choice {
          case a {
            leaf op {
              type string;
            }
            leaf port {
              type string;
            }
          }
          case b {
            leaf range {
              type empty;
            }
            leaf start {
              type string;
            }
            leaf end {
              type string;
            }
          }
        }
      }
    }
  }

  grouping ncs_template_queue-override-grouping {
    list queue {
      // NCS patched for predictable order
      ordered-by user;
      key "queue-id";
      leaf queue-id {
        type string;
      }
      container adaption-rule {
        leaf pir {
          type ncs_template_adaption-rule;
        }
        leaf cir {
          type ncs_template_adaption-rule;
        }
      }
      leaf avg-frame-overhead {
        type string;
      }
      container mbs {
        leaf val {
          type string;
        }
        leaf unit {
          type string;
        }
      }
      leaf cbs {
        type string;
      }
      leaf high-prio-only {
        type string;
      }
      container rate {
        leaf pir {
          type string;
        }
        leaf cir {
          type string;
        }
      }
      container parent {
        leaf weight {
          type string;
        }
        leaf cir-weight {
          type string;
        }
      }
      container percent-rate {
        leaf pir {
          type string;
        }
        leaf cir {
          type string;
        }
      }
    }
  }

  grouping ncs_template_ip-criteria-grouping {
    leaf match-criteria {
      type string;
    }
    list entry {
      // NCS patched for predictable order
      ordered-by user;
      key "id";
      leaf id {
        type string;
      }
      leaf description {
        type string;
      }
      container match {
        leaf protocol {
          type ncs_template_protocol;
        }
        leaf dscp {
          type string;
        }
        leaf dst-ip {
          type string;
        }
        leaf src-ip {
          type string;
        }
        container dst-port {
          choice port-choice {
            case a {
              leaf op {
                type string;
              }
              leaf port {
                type string;
              }
            }
            case b {
              leaf range {
                type empty;
              }
              leaf start {
                type string;
              }
              leaf end {
                type string;
              }
            }
          }
        }
        container src-port {
          choice port-choice {
            case a {
              leaf op {
                type string;
              }
              leaf port {
                type string;
              }
            }
            case b {
              leaf range {
                type empty;
              }
              leaf start {
                type string;
              }
              leaf end {
                type string;
              }
            }
          }
        }
      }
      container action {
        leaf fc {
          type string;
        }
        leaf priority {
          type string;
        }
      }
    }
  }

  grouping ncs_template_ipv6-criteria-grouping {
    list entry {
      // NCS patched for predictable order
      ordered-by user;
      key "id";
      leaf id {
        type string;
      }
      leaf description {
        type string;
      }
      container match {
        leaf protocol {
          type ncs_template_protocol;
        }
        leaf dst-ip {
          type string;
        }
        leaf src-ip {
          type string;
        }
        container dst-port {
          choice port-choice {
            case a {
              leaf op {
                type string;
              }
              leaf port {
                type string;
              }
            }
            case b {
              leaf range {
                type empty;
              }
              leaf start {
                type string;
              }
              leaf end {
                type string;
              }
            }
          }
        }
        container src-port {
          choice port-choice {
            case a {
              leaf op {
                type string;
              }
              leaf port {
                type string;
              }
            }
            case b {
              leaf range {
                type empty;
              }
              leaf start {
                type string;
              }
              leaf end {
                type string;
              }
            }
          }
        }
      }
      container action {
        leaf fc {
          type string;
        }
        leaf priority {
          type string;
        }
      }
    }
  }

  grouping ncs_template_meter-grouping {
    leaf meter-id {
      type string;
    }
    leaf multipoint {
      type empty;
    }
    container adaptation-rule {
      leaf cir {
        type string;
      }
      leaf pir {
        type string;
      }
    }
    container cbs {
      leaf size {
        type string;
      }
    }
    container mbs {
      leaf size {
        type string;
      }
    }
    container rate {
      leaf pir {
        type string;
      }
      leaf cir {
        type string;
      }
    }
    leaf mode {
      type string;
    }
  }

  grouping ncs_template_cpm-filter-match-port-grouping {
    choice port-choice {
      case a {
        leaf port-number {
          type string;
        }
        leaf mask {
          type string;
        }
      }
      case b {
        leaf range {
          type empty;
        }
        leaf start {
          type string;
        }
        leaf end {
          type string;
        }
      }
      case c {
        leaf port-list {
          type string;
        }
      }
    }
  }

  grouping ncs_template_filter-match-ip-grouping {
    choice ip {
      leaf address {
        type string;
      }
      leaf ip-prefix-list {
        type string;
      }
    }
  }

  grouping ncs_template_filter-match-ipv6-grouping {
    choice ipv6 {
      leaf address {
        type string;
      }
      leaf ipv6-prefix-list {
        type string;
      }
    }
  }

  grouping ncs_template_sap-egress-grouping {
    leaf agg-rate-limit {
      type string;
    }
    container filter {
      uses ncs_template_filter-choice;
    }
    leaf multicast-group {
      type string;
    }
    leaf qos {
      type string;
    }
    leaf scheduler-policy {
      // NCS drop tailf-common:cli-diff-dependency statement
      type string;
    }
    container scheduler-override {
      leaf scheduler {
        type string;
      }
    }
    leaf qinq-mark-top-only {
      type empty;
    }
  }

  grouping ncs_template_sap-ingress-grouping {
    container filter {
      uses ncs_template_filter-choice;
    }
    leaf match-qinq-dot1p {
      type string;
    }
    leaf qos {
      type string;
    }
    leaf scheduler-policy {
      type string;
    }
    container scheduler-override {
      leaf scheduler {
        type string;
      }
    }
    leaf vlan-translation {
      type string;
    }
  }

  grouping ncs_template_policy-options-action-grouping {
    choice action {
      leaf reject {
        type empty;
      }
      container other {
        leaf action {
          type string;
        }
        leaf aigp-metric {
          type string;
        }
        container as-path {
          leaf action {
            type string;
          }
          leaf name {
            type string;
          }
        }
        container as-path-prepend {
          leaf as-number {
            type string;
          }
          leaf repeat {
            type string;
          }
        }
        container community {
          leaf action {
            type string;
          }
          leaf name {
            type string;
          }
        }
        container damping {
          choice damping {
            leaf none {
              type empty;
            }
            leaf name {
              type string;
            }
          }
        }
        leaf local-preference {
          type string;
        }
        container metric {
          leaf action {
            type string;
          }
          leaf metric {
            type string;
          }
        }
        container multicast-redirect {
          leaf fwd-service {
            type string;
          }
          leaf ip-int-name {
            type string;
          }
        }
        leaf next-hop {
          type string;
        }
        leaf next-hop-self {
          type empty;
        }
        leaf origin {
          type string;
        }
        leaf preference {
          type string;
        }
        leaf tag {
          type string;
        }
        leaf type {
          type string;
        }
      }
    }
  }

  grouping ncs_template_queue-group-template-entry {
    leaf queue-group-name {
      type string;
    }
    leaf description {
      type string;
    }
    list fc {
      // NCS patched for predictable order
      ordered-by user;
      key "fc-name";
      leaf fc-name {
        type string;
      }
      leaf queue {
        type string;
      }
    }
    list policer {
      // NCS patched for predictable order
      ordered-by user;
      key "policer-id";
      leaf policer-id {
        type string;
      }
      container adaptation-rule {
        leaf pir {
          type string;
        }
        leaf cir {
          type string;
        }
      }
      leaf adv-config-policy {
        type string;
      }
      container cbs {
        leaf size {
          type string;
        }
        leaf unit {
          type string;
        }
      }
      leaf description {
        type string;
      }
      leaf high-prio-only {
        type string;
      }
      container mbs {
        leaf size {
          type string;
        }
        leaf unit {
          type string;
        }
      }
      container packet-byte-offset {
        choice add-delete {
          leaf add {
            type string;
          }
          leaf subtract {
            type string;
          }
        }
      }
      container parent {
        leaf name {
          type string;
        }
        leaf level {
          type string;
        }
        leaf weight-level {
          type string;
        }
      }
      leaf profile-capped {
        type empty;
      }
      container rate {
        leaf pir {
          type string;
        }
        leaf cir {
          type string;
        }
      }
      leaf stat-mode {
        type string;
      }
    }
    list queue {
      // NCS patched for predictable order
      ordered-by user;
      key "queue-id";
      leaf queue-id {
        type string;
      }
      container adaptation-rule {
        leaf pir {
          type string;
        }
        leaf cir {
          type string;
        }
      }
      leaf adv-config-policy {
        type string;
      }
      leaf burst-limit {
        type string;
      }
      leaf cbs {
        type string;
      }
      leaf high-prio-only {
        type string;
      }
      leaf mbs {
        type string;
      }
      container parent {
        leaf name {
          type string;
        }
        leaf weight {
          type string;
        }
        leaf level {
          type string;
        }
        leaf cir-weight {
          type string;
        }
        leaf cir-level {
          type string;
        }
      }
      container percent-rate {
        leaf pir-percent {
          type string;
        }
        leaf cir {
          type string;
        }
      }
      leaf pool {
        type string;
      }
      container port-parent {
        leaf weight {
          type string;
        }
        leaf level {
          type string;
        }
        leaf cir-weight {
          type string;
        }
        leaf cir-level {
          type string;
        }
      }
      container rate {
        leaf pir {
          type string;
        }
        leaf cir {
          type string;
        }
      }
    }
  }

  grouping ncs_template_dhcp-lease-time {
    leaf days {
      type string;
    }
    leaf hrs {
      type string;
    }
    leaf min {
      type string;
    }
    leaf sec {
      type string;
    }
  }

  grouping ncs_rpc_notif_src-dst-ip {
    leaf src-ip {
      type union {
        type inet:ipv4-prefix;
        type string;
      }
    }
    leaf dst-ip {
      type union {
        type inet:ipv4-prefix;
        type string;
      }
    }
  }

  grouping ncs_rpc_notif_ip-address-range {
    list low-high-list {
      tailf:cli-drop-node-name;
      tailf:cli-suppress-mode;
      tailf:cli-delete-when-empty;
      key "low high";
      leaf low {
        type inet:ipv4-address {
          tailf:info
            "<start-ip-address>";
        }
      }
      leaf high {
        type inet:ipv4-address {
          tailf:info
            "<stop-ip-address>";
        }
      }
    }
  }

  grouping ncs_rpc_notif_eth-cfm {
    list mep {
      tailf:info
        "Configure a CFM Virtual Maintenance Endpoint";
      tailf:cli-embed-no-on-delete;
      tailf:cli-sequence-commands;
      key "mep-id";
      leaf mep-id {
        tailf:info
          "mep-id;;<1..8191>";
        mandatory true;
        type uint16 {
          range "1..8191";
        }
      }
      leaf domain {
        tailf:cli-hide-in-submode;
        tailf:info
          "md-index;;<1..4294967295>";
        type string;
        mandatory true;
      }
      leaf association {
        tailf:cli-hide-in-submode;
        tailf:info
          "ma-index;;<1..4294967295>";
        type string;
        mandatory true;
      }
      leaf direction {
        tailf:info
          "<up | down>";
        tailf:cli-hide-in-submode;
        tailf:cli-no-name-on-delete;
        tailf:cli-no-value-on-delete;
        type ncs_rpc_notif_direction;
      }
      container ais-enable {
        tailf:cli-add-mode;
        tailf:cli-embed-no-on-delete;
        tailf:cli-break-sequence-commands;
        leaf-list client-meg-level {
          tailf:cli-flat-list-syntax;
          tailf:cli-no-value-on-delete;
          type uint8 {
            range "1..7";
          }
        }
        leaf description {
          tailf:cli-embed-no-on-delete;
          type string;
        }
        leaf interval {
          tailf:cli-embed-no-on-delete;
          type enumeration {
            enum "1";
            enum "60";
          }
        }
        leaf priority {
          tailf:cli-embed-no-on-delete;
          type uint8 {
            range "0..7";
          }
        }
      }
      leaf ccm-enable {
        tailf:info
          "Enable/Disable Generation of CCM messages";
        tailf:cli-embed-no-on-delete;
        type empty;
      }
      leaf ccm-ltm-priority {
        tailf:info
          "Configure the priority of CCM and LTM messages";
        tailf:cli-embed-no-on-delete;
        type uint8 {
          range "0..7";
        }
      }
      leaf ccm-padding-size {
        tailf:info
          "Insert additional padding in the CCM packets";
        tailf:cli-embed-no-on-delete;
        type uint32;
      }
      leaf description {
        tailf:info
          "Add/remove a text description for the MEP";
        tailf:cli-embed-no-on-delete;
        type string;
      }
      container eth-test-enable {
        tailf:info
          "Enable/Disable eth-test functionality on MEP";
        tailf:cli-add-mode;
        tailf:cli-embed-no-on-delete;
        uses ncs_rpc_notif_eth-test;
      }
      leaf fault-propagation-enable {
        tailf:info
          "Configure the Fault Propagation for the MEP";
        tailf:cli-embed-no-on-delete;
        type enumeration {
          enum "use-if-tlv";
          enum "suspend-ccm";
        }
      }
      leaf low-priority-defect {
        tailf:info
          "Configure the Lowest Priority Defect for the MEP";
        type enumeration {
          enum "allDef";
          enum "macRemErrXcon";
          enum "remErrXcon";
          enum "errXcon";
          enum "Xcon";
          enum "noXcon";
        }
      }
      leaf mac-address {
        tailf:info
          "Configure the MAC Address for the MEP";
        tailf:cli-embed-no-on-delete;
        type ncs_rpc_notif_ieee-mac;
      }
      leaf one-way-delay-threshold {
        tailf:info
          "Configure the one-way-delay test threshold";
        type uint16 {
          range "0..600";
        }
      }
      leaf shutdown {
        tailf:info
          "Administratively enable/disable the MEP";
        tailf:cli-boolean-no;
        default "true";
        type boolean;
      }
    }
  }

  grouping ncs_rpc_notif_igmp-snooping {
    leaf disable-router-alert {
      tailf:cli-embed-no-on-delete;
      type empty;
    }
    leaf fast-leave {
      tailf:cli-embed-no-on-delete;
      type empty;
    }
    leaf import {
      tailf:cli-embed-no-on-delete;
      type string {
        length "1..32";
      }
    }
    leaf last-member-query-interval {
      tailf:cli-embed-no-on-delete;
      type uint8 {
        range "1..50";
      }
    }
    leaf max-num-groups {
      tailf:cli-embed-no-on-delete;
      type uint16 {
        range "1..1000";
      }
    }
    leaf mrouter-port {
      tailf:cli-embed-no-on-delete;
      type empty;
    }
    leaf query-interval {
      tailf:info
        "Configure the IGMP Query Interval for v1/v2 Queriers";
      tailf:cli-embed-no-on-delete;
      type uint16 {
        range "2..1024";
      }
    }
    leaf query-response-interval {
      tailf:cli-embed-no-on-delete;
      type uint16 {
        range "1..1023";
      }
    }
    leaf robust-count {
      tailf:cli-embed-no-on-delete;
      type uint8 {
        range "1..255";
      }
    }
    leaf send-queries {
      tailf:cli-embed-no-on-delete;
      type empty;
    }
    container static {
      tailf:cli-add-mode;
      list group {
        tailf:cli-embed-no-on-delete;
        max-elements 1;
        key "group-address";
        leaf group-address {
          tailf:cli-hide-in-submode;
          type inet:ip-address;
        }
        leaf stdarg {
          tailf:cli-embed-no-on-delete;
          type string;
        }
      }
    }
    leaf version {
      tailf:cli-embed-no-on-delete;
      type uint8;
    }
  }

  grouping ncs_rpc_notif_sdp-common {
    leaf sdp-id {
      // NCS drop tailf-common:non-strict-leafref statement
      type uint32;
    }
    leaf vc-id {
      type uint32;
    }
    leaf vc-type {
      tailf:cli-hide-in-submode;
      tailf:cli-no-name-on-delete;
      tailf:cli-no-value-on-delete;
      type enumeration {
        enum "ether";
        enum "vlan";
      }
    }
    leaf endpoint {
      tailf:cli-hide-in-submode;
      tailf:cli-no-name-on-delete;
      tailf:cli-no-value-on-delete;
      // NCS drop tailf-common:non-strict-leafref statement
      type string;
    }
    leaf shutdown {
      tailf:cli-boolean-no;
      default "false";
      type boolean;
    }
  }

  grouping ncs_rpc_notif_sdp-spoke-mesh-common {
    uses ncs_rpc_notif_sdp-common;
    leaf accounting-policy {
      tailf:info
        "Configure accounting-policy to be used";
      tailf:cli-no-value-on-delete;
      type uint8 {
        range "1..99";
      }
    }
    leaf auto-learn-mac-protect {
      tailf:info
        "Enable/disable automatic update of MAC protect list";
      tailf:cli-embed-no-on-delete;
      type empty;
    }
    leaf collect-stats {
      tailf:info
        "Enable/disable statistics collection";
      tailf:cli-embed-no-on-delete;
      type empty;
    }
    container egress {
      tailf:info
        "SDP binding egress configuration";
      tailf:cli-add-mode;
      container filter {
        tailf:info
          "Apply egress filter";
        tailf:cli-embed-no-on-delete;
        uses ncs_rpc_notif_filter-choice;
      }
      container qos {
        tailf:info
          "Configure egress qos";
        tailf:cli-embed-no-on-delete;
        tailf:cli-sequence-commands;
        tailf:cli-compact-syntax;
        leaf network-policy-id {
          tailf:info
            "<network-policy-id>";
          tailf:cli-drop-node-name;
          tailf:cli-no-value-on-delete;
          type uint16;
          // NCS drop tailf-common:non-strict-leafref statement
        }
        leaf port-redirect-group {
          tailf:info
            "<queue-group-name>";
          tailf:cli-no-name-on-delete;
          tailf:cli-no-value-on-delete;
          // NCS drop tailf-common:non-strict-leafref statement
          type string;
        }
        leaf instance {
          tailf:info
            "<instance-id>";
          tailf:cli-no-name-on-delete;
          tailf:cli-no-value-on-delete;
          type uint16 {
            range "1..16384";
          }
        }
      }
      leaf vc-label {
        tailf:info
          "Configure egress label";
        type uint32 {
          range "16..1048575";
        }
      }
    }
    container eth-cfm {
      tailf:info
        "Configure CFM parameters";
      tailf:cli-add-mode;
      uses ncs_rpc_notif_eth-cfm;
    }
    leaf force-vlan-forwarding {
      tailf:info
        "Forces vlan-vc-type forwarding in the data-path";
      type empty;
    }
    container igmp-snooping {
      tailf:info
        "Configure IGMP snooping parameters";
      uses ncs_rpc_notif_igmp-snooping;
    }
    container ingress {
      tailf:info
        "SDP binding ingress configuration";
      tailf:cli-add-mode;
      container filter {
        tailf:info
          "Apply ingress filter";
        tailf:cli-embed-no-on-delete;
        uses ncs_rpc_notif_filter-choice;
      }
      container qos {
        tailf:info
          "Configure egress qos";
        tailf:cli-embed-no-on-delete;
        tailf:cli-sequence-commands;
        tailf:cli-compact-syntax;
        leaf network-policy-id {
          tailf:info
            "<network-policy-id>";
          tailf:cli-drop-node-name;
          tailf:cli-no-value-on-delete;
          type uint16;
          // NCS drop tailf-common:non-strict-leafref statement
        }
        leaf fp-redirect-group {
          tailf:info
            "<queue-group-name>";
          tailf:cli-no-name-on-delete;
          tailf:cli-no-value-on-delete;
          // NCS drop tailf-common:non-strict-leafref statement
          type string;
        }
        leaf instance {
          tailf:info
            "<instance-id>";
          tailf:cli-no-name-on-delete;
          tailf:cli-no-value-on-delete;
          type uint16 {
            range "1..16384";
          }
        }
      }
      leaf vc-label {
        tailf:info
          "Configure egress label";
        type uint32 {
          range "16..1048575";
        }
      }
    }
    leaf mac-pinning {
      tailf:info
        "Enable/disable MAC address pinning";
      type empty;
    }
    list static-mac {
      tailf:info
        "Configure a static mac entry";
      tailf:cli-embed-no-on-delete;
      tailf:cli-suppress-mode;
      key "address";
      leaf address {
        type ncs_rpc_notif_ieee-mac;
      }
    }
    leaf restrict-protected-src {
      tailf:info
        "Enable/disable protected src MAC restriction";
      tailf:cli-no-value-on-delete;
      type enumeration {
        enum "alarm-only";
        enum "discard-frame";
      }
    }
    leaf vlan-vc-tag {
      type uint16 {
        range "0..4094";
      }
    }
  }

  grouping ncs_rpc_notif_stp-common {
    leaf auto-edge {
      tailf:info
        "Enable/disable automatic detection of edge port";
      tailf:cli-embed-no-on-delete;
      type empty;
    }
    leaf edge-port {
      tailf:info
        "Configure spoke-sdp as edge port";
      tailf:cli-embed-no-on-delete;
      type empty;
    }
    leaf link-type {
      tailf:info
        "Configure link type of the spoke-sdp";
      tailf:cli-embed-no-on-delete;
      type enumeration {
        enum "pt-pt";
        enum "shared";
      }
    }
    leaf path-cost {
      tailf:info
        "Configure path-cost";
      tailf:cli-no-name-on-delete;
      type uint32 {
        range "1..200000000";
      }
    }
    leaf port-num {
      tailf:info
        "Configure virtual port number";
      tailf:cli-embed-no-on-delete;
      type uint16;
    }
    leaf priority {
      tailf:info
        "Configure stp priority";
      tailf:cli-embed-no-on-delete;
      type uint16 {
        range "4096..65535";
      }
    }
    leaf shutdown {
      tailf:info
        "Enable/disable spanning tree protocol";
      tailf:cli-boolean-no;
      default "true";
      type boolean;
    }
  }

  grouping ncs_rpc_notif_filter-choice {
    choice filter {
      leaf ip {
        tailf:info
          "<ip-filter-id>;;[1..65535]|<name:64 char max>";
        // NCS drop tailf-common:non-strict-leafref statement
        type string;
      }
      leaf ipv6 {
        tailf:info
          "<ipv6-filter-id>;;[1..65535]|<name:64 char max>";
        // NCS drop tailf-common:non-strict-leafref statement
        type string;
      }
      leaf mac {
        tailf:info
          "<mac-filter-id>;;[1..65535]|<name:64 char max>";
        // NCS drop tailf-common:non-strict-leafref statement
        type string;
      }
    }
  }

  grouping ncs_rpc_notif_eth-test {
    leaf test-pattern {
      tailf:cli-embed-no-on-delete;
      type ncs_rpc_notif_test-pattern;
    }
    leaf crc-enable {
      type empty;
      when '../test-pattern' {
        tailf:xpath-root 3;
      }
    }
  }

  grouping ncs_rpc_notif_time-stamp {
    leaf start-week {
      tailf:cli-drop-node-name;
      type enumeration {
        enum "first";
        enum "second";
        enum "third";
        enum "fourth";
        enum "last";
      }
    }
    leaf start-day {
      tailf:cli-drop-node-name;
      type enumeration {
        enum "sunday";
        enum "monday";
        enum "tuesday";
        enum "wednesday";
        enum "thursday";
        enum "friday";
        enum "saturday";
      }
    }
    leaf month {
      tailf:cli-drop-node-name;
      type enumeration {
        enum "january";
        enum "february";
        enum "march";
        enum "april";
        enum "may";
        enum "june";
        enum "july";
        enum "august";
        enum "september";
        enum "october";
        enum "november";
        enum "december";
      }
    }
    leaf hours-minutes {
      tailf:cli-drop-node-name;
      type string;
    }
  }

  grouping ncs_rpc_notif_ip-filter-entry-grouping {
    leaf entry-name {
      type string;
    }
    leaf description {
      tailf:cli-no-name-on-delete;
      type string {
        length "1..80";
      }
    }
    leaf log {
      tailf:cli-embed-no-on-delete;
      type uint16;
    }
    container match {
      tailf:cli-add-mode;
      leaf protocol {
        tailf:cli-hide-in-submode;
        type ncs_rpc_notif_protocol;
      }
      leaf dscp {
        type ncs_rpc_notif_dscp-type;
      }
      container src-ip {
        tailf:cli-embed-no-on-delete;
        tailf:cli-compact-syntax;
        tailf:cli-sequence-commands;
        uses ncs_rpc_notif_filter-match-ip-grouping;
      }
      container dst-ip {
        tailf:cli-embed-no-on-delete;
        tailf:cli-compact-syntax;
        tailf:cli-sequence-commands;
        uses ncs_rpc_notif_filter-match-ip-grouping;
      }
      leaf icmp-type {
        type ncs_rpc_notif_icmp-type;
      }
      leaf icmp-code {
        type uint32;
      }
      leaf fragment {
        type boolean;
      }
      container ip-option {
        tailf:cli-compact-syntax;
        leaf a {
          tailf:cli-drop-node-name;
          type uint32;
        }
        leaf b {
          tailf:cli-drop-node-name;
          type uint32;
        }
      }
      container dst-port {
        tailf:cli-compact-syntax;
        tailf:cli-sequence-commands;
        tailf:cli-embed-no-on-delete;
        choice port-choice {
          case a {
            leaf op {
              tailf:info
                "operators";
              tailf:cli-drop-node-name;
              tailf:cli-no-value-on-delete;
              type enumeration {
                enum "lt";
                enum "gt";
                enum "eq";
              }
            }
            leaf port {
              tailf:info
                "port number";
              tailf:cli-drop-node-name;
              tailf:cli-no-value-on-delete;
              mandatory true;
              type uint16;
            }
          }
          case b {
            leaf range {
              tailf:info
                "port range";
              type empty;
            }
            leaf start {
              tailf:info
                "start";
              tailf:cli-drop-node-name;
              tailf:cli-no-value-on-delete;
              mandatory true;
              type uint16;
            }
            leaf end {
              tailf:info
                "end";
              tailf:cli-drop-node-name;
              tailf:cli-no-value-on-delete;
              mandatory true;
              type uint16;
            }
          }
        }
      }
      container src-port {
        tailf:cli-compact-syntax;
        tailf:cli-sequence-commands;
        tailf:cli-embed-no-on-delete;
        choice port-choice {
          case a {
            leaf op {
              tailf:cli-drop-node-name;
              tailf:cli-no-value-on-delete;
              type enumeration {
                enum "lt";
                enum "gt";
                enum "eq";
              }
            }
            leaf port {
              tailf:cli-drop-node-name;
              tailf:cli-no-value-on-delete;
              mandatory true;
              type uint16;
            }
          }
          case b {
            leaf range {
              type empty;
            }
            leaf start {
              tailf:cli-drop-node-name;
              tailf:cli-no-value-on-delete;
              mandatory true;
              type uint16;
            }
            leaf end {
              tailf:cli-drop-node-name;
              tailf:cli-no-value-on-delete;
              mandatory true;
              type uint16;
            }
          }
          case c {
            leaf src-port-number {
              tailf:cli-drop-node-name;
              type uint16;
            }
            leaf mask {
              tailf:cli-drop-node-name;
              mandatory true;
              type uint16;
            }
          }
        }
      }
    }
  }

  grouping ncs_rpc_notif_ipv6-filter-entry-grouping {
    leaf entry-name {
      type string;
    }
    leaf description {
      type string;
    }
    container match {
      tailf:cli-add-mode;
      leaf next-header {
        tailf:cli-hide-in-submode;
        type enumeration {
          enum "*";
          enum "none";
          enum "icmp";
          enum "igmp";
          enum "ip";
          enum "tcp";
          enum "egp";
          enum "igp";
          enum "udp";
          enum "rdp";
          enum "ipv6";
          enum "idrp";
          enum "rsvp";
          enum "gre";
          enum "ipv6-icmp";
          enum "ipv6-no-nxt";
          enum "iso-ip";
          enum "eigrp";
          enum "ospf-igp";
          enum "ether-ip";
          enum "encap";
          enum "pnni";
          enum "pim";
          enum "vrrp";
          enum "l2tp";
          enum "stp";
          enum "ptp";
          enum "isis";
          enum "crtp";
          enum "crudp";
          enum "sctp";
        }
      }
      leaf dscp {
        type ncs_rpc_notif_dscp-type;
      }
      container src-ip {
        tailf:cli-embed-no-on-delete;
        tailf:cli-compact-syntax;
        tailf:cli-sequence-commands;
        uses ncs_rpc_notif_filter-match-ipv6-grouping;
      }
      container dst-ip {
        tailf:cli-embed-no-on-delete;
        tailf:cli-compact-syntax;
        tailf:cli-sequence-commands;
        uses ncs_rpc_notif_filter-match-ipv6-grouping;
      }
      leaf icmp-type {
        type ncs_rpc_notif_icmpv6-type;
      }
      leaf icmp-code {
        type uint32;
      }
      leaf fragment {
        type boolean;
      }
      container ip-option {
        tailf:cli-compact-syntax;
        leaf a {
          tailf:cli-drop-node-name;
          type uint32;
        }
        leaf b {
          tailf:cli-drop-node-name;
          type uint32;
        }
      }
      container dst-port {
        tailf:cli-compact-syntax;
        tailf:cli-sequence-commands;
        choice port-choice {
          case a {
            leaf op {
              tailf:cli-drop-node-name;
              type enumeration {
                enum "lt";
                enum "gt";
                enum "eq";
              }
            }
            leaf port {
              tailf:cli-drop-node-name;
              type uint16;
            }
          }
          case b {
            leaf range {
              type empty;
            }
            leaf start {
              tailf:cli-drop-node-name;
              type uint16;
            }
            leaf end {
              tailf:cli-drop-node-name;
              type uint16;
            }
          }
        }
      }
      container src-port {
        tailf:cli-compact-syntax;
        tailf:cli-sequence-commands;
        choice port-choice {
          case a {
            leaf op {
              tailf:cli-drop-node-name;
              type enumeration {
                enum "lt";
                enum "gt";
                enum "eq";
              }
            }
            leaf port {
              tailf:cli-drop-node-name;
              type uint16;
            }
          }
          case b {
            leaf range {
              type empty;
            }
            leaf start {
              tailf:cli-drop-node-name;
              type uint16;
            }
            leaf end {
              tailf:cli-drop-node-name;
              type uint16;
            }
          }
        }
      }
    }
  }

  grouping ncs_rpc_notif_queue-override-grouping {
    list queue {
      tailf:cli-embed-no-on-delete;
      key "queue-id";
      leaf queue-id {
        type uint32;
      }
      container adaption-rule {
        tailf:cli-compact-syntax;
        tailf:cli-sequence-commands;
        tailf:cli-embed-no-on-delete;
        leaf pir {
          type ncs_rpc_notif_adaption-rule;
        }
        leaf cir {
          type ncs_rpc_notif_adaption-rule;
        }
      }
      leaf avg-frame-overhead {
        tailf:cli-embed-no-on-delete;
        type decimal64 {
          fraction-digits 2;
          range "0..100";
        }
      }
      container mbs {
        tailf:cli-compact-syntax;
        tailf:cli-sequence-commands;
        tailf:cli-embed-no-on-delete;
        leaf val {
          tailf:cli-drop-node-name;
          type union {
            type enumeration {
              enum "default";
            }
            type uint32 {
              range "0..134217728";
            }
          }
        }
        leaf unit {
          tailf:cli-drop-node-name;
          type enumeration {
            enum "bytes";
            enum "kilobytes";
          }
        }
      }
      leaf cbs {
        tailf:cli-embed-no-on-delete;
        type union {
          type enumeration {
            enum "default";
          }
          type uint32 {
            range "0..131072";
          }
        }
      }
      leaf high-prio-only {
        type union {
          type enumeration {
            enum "default";
          }
          type uint8;
        }
      }
      container rate {
        tailf:cli-compact-syntax;
        tailf:cli-sequence-commands;
        tailf:cli-embed-no-on-delete;
        leaf pir {
          tailf:cli-drop-node-name;
          type union {
            type enumeration {
              enum "max";
            }
            type uint32 {
              range "1..100000000";
            }
          }
        }
        leaf cir {
          type union {
            type enumeration {
              enum "max";
            }
            type uint32 {
              range "0..100000000";
            }
          }
        }
      }
      container parent {
        tailf:cli-compact-syntax;
        tailf:cli-sequence-commands;
        tailf:cli-embed-no-on-delete;
        leaf weight {
          type uint8 {
            range "0..100";
          }
        }
        leaf cir-weight {
          type uint8 {
            range "0..100";
          }
        }
      }
      container percent-rate {
        tailf:cli-compact-syntax;
        tailf:cli-sequence-commands;
        tailf:cli-embed-no-on-delete;
        leaf pir {
          tailf:cli-drop-node-name;
          type decimal64 {
            fraction-digits 2;
            range "0..100";
          }
        }
        leaf cir {
          type decimal64 {
            fraction-digits 2;
            range "0..100";
          }
        }
      }
    }
  }

  grouping ncs_rpc_notif_ip-criteria-grouping {
    leaf match-criteria {
      tailf:cli-hide-in-submode;
      tailf:cli-drop-node-name;
      tailf:cli-no-value-on-delete;
      type enumeration {
        enum "any";
        enum "dscp-only";
      }
    }
    list entry {
      key "id";
      leaf id {
        type uint16;
      }
      leaf description {
        tailf:cli-embed-no-on-delete;
        type string;
      }
      container match {
        tailf:cli-add-mode;
        leaf protocol {
          tailf:cli-hide-in-submode;
          type ncs_rpc_notif_protocol;
        }
        leaf dscp {
          type string;
        }
        leaf dst-ip {
          type tailf:ipv4-address-and-prefix-length;
        }
        leaf src-ip {
          type tailf:ipv4-address-and-prefix-length;
        }
        container dst-port {
          tailf:cli-compact-syntax;
          tailf:cli-sequence-commands;
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container src-port {
          tailf:cli-compact-syntax;
          tailf:cli-sequence-commands;
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
      }
      container action {
        tailf:cli-compact-syntax;
        leaf fc {
          type string;
        }
        leaf priority {
          type enumeration {
            enum "high";
            enum "low";
          }
        }
      }
    }
  }

  grouping ncs_rpc_notif_ipv6-criteria-grouping {
    list entry {
      key "id";
      leaf id {
        type uint16;
      }
      leaf description {
        type string;
      }
      container match {
        tailf:cli-add-mode;
        leaf protocol {
          tailf:cli-hide-in-submode;
          type ncs_rpc_notif_protocol;
        }
        leaf dst-ip {
          type tailf:ipv6-address-and-prefix-length;
        }
        leaf src-ip {
          type tailf:ipv6-address-and-prefix-length;
        }
        container dst-port {
          tailf:cli-compact-syntax;
          tailf:cli-sequence-commands;
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container src-port {
          tailf:cli-compact-syntax;
          tailf:cli-sequence-commands;
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
      }
      container action {
        tailf:cli-compact-syntax;
        leaf fc {
          type string;
        }
        leaf priority {
          type enumeration {
            enum "high";
            enum "low";
          }
        }
      }
    }
  }

  grouping ncs_rpc_notif_meter-grouping {
    leaf meter-id {
      type uint8 {
        range "1..32";
      }
    }
    leaf multipoint {
      tailf:cli-hide-in-submode;
      tailf:cli-no-name-on-delete;
      type empty;
    }
    container adaptation-rule {
      tailf:info
        "Specify the CIR and PIR adaptation rules";
      tailf:cli-embed-no-on-delete;
      tailf:cli-compact-syntax;
      leaf cir {
        tailf:cli-no-name-on-delete;
        tailf:cli-no-value-on-delete;
        type enumeration {
          enum "max";
          enum "min";
          enum "closest";
        }
      }
      leaf pir {
        tailf:cli-no-name-on-delete;
        tailf:cli-no-value-on-delete;
        type enumeration {
          enum "max";
          enum "min";
          enum "closest";
        }
      }
    }
    container cbs {
      tailf:info
        "Specify CBS";
      tailf:cli-compact-syntax;
      leaf size {
        tailf:cli-drop-node-name;
        tailf:cli-no-value-on-delete;
        type union {
          type uint32 {
            range "4..2146959";
          }
          type enumeration {
            enum "default";
          }
        }
      }
    }
    container mbs {
      tailf:info
        "Specify MBS";
      tailf:cli-compact-syntax;
      leaf size {
        tailf:cli-drop-node-name;
        tailf:cli-no-value-on-delete;
        type union {
          type uint32 {
            range "4..2146959";
          }
          type enumeration {
            enum "default";
          }
        }
      }
    }
    container rate {
      tailf:info
        "Specify rates (CIR and PIR)";
      tailf:cli-compact-syntax;
      tailf:cli-embed-no-on-delete;
      leaf pir {
        tailf:cli-no-value-on-delete;
        type union {
          type uint32 {
            range "0..20000000";
          }
          type enumeration {
            enum "max";
          }
        }
      }
      leaf cir {
        tailf:cli-no-value-on-delete;
        type union {
          type uint32 {
            range "0..20000000";
          }
          type enumeration {
            enum "max";
          }
        }
      }
    }
    leaf mode {
      tailf:info
        "Specify rate mode";
      type enumeration {
        enum "trtcm1";
        enum "trtcm2";
        enum "srtcm";
      }
    }
  }

  grouping ncs_rpc_notif_cpm-filter-match-port-grouping {
    choice port-choice {
      case a {
        leaf port-number {
          tailf:info
            "<tcp/udp port-number>";
          tailf:cli-drop-node-name;
          tailf:cli-no-value-on-delete;
          type uint16;
        }
        leaf mask {
          tailf:info
            "<tcp/udp port mask>";
          tailf:cli-drop-node-name;
          tailf:cli-no-value-on-delete;
          type uint16;
        }
      }
      case b {
        leaf range {
          tailf:info
            "range <tcp/udp port-number> <tcp/udp port-number>";
          type empty;
        }
        leaf start {
          tailf:cli-drop-node-name;
          type uint16;
        }
        leaf end {
          tailf:cli-drop-node-name;
          type uint16;
        }
      }
      case c {
        leaf port-list {
          tailf:info
            "port-list <port-list-name>";
          type string {
            length "1..32";
          }
        }
      }
    }
  }

  grouping ncs_rpc_notif_filter-match-ip-grouping {
    choice ip {
      leaf address {
        tailf:info
          "<ip-address/prefix-length> | <ip-address>";
        tailf:cli-drop-node-name;
        tailf:cli-no-value-on-delete;
        type union {
          type inet:ipv4-address;
          type inet:ipv4-prefix;
          type string;
        }
      }
      leaf ip-prefix-list {
        tailf:info
          "ip-prefix-list <prefix-list-name>";
        tailf:cli-no-value-on-delete;
        tailf:cli-no-name-on-delete;
        type string;
      }
    }
  }

  grouping ncs_rpc_notif_filter-match-ipv6-grouping {
    choice ipv6 {
      leaf address {
        tailf:info
          "<ipv6-address/prefix-length> | <ipv6-address>";
        tailf:cli-drop-node-name;
        tailf:cli-no-value-on-delete;
        type union {
          type tailf:ipv6-address-and-prefix-length;
          type inet:ipv6-address;
          type string;
        }
      }
      leaf ipv6-prefix-list {
        tailf:info
          "ipv6-prefix-list <prefix-list-name>";
        tailf:cli-no-value-on-delete;
        tailf:cli-no-name-on-delete;
        type string;
      }
    }
  }

  grouping ncs_rpc_notif_sap-egress-grouping {
    leaf agg-rate-limit {
      tailf:cli-embed-no-on-delete;
      tailf:cli-no-value-on-delete;
      type uint32 {
        range "1..40000000";
      }
    }
    container filter {
      tailf:cli-embed-no-on-delete;
      uses ncs_rpc_notif_filter-choice;
    }
    leaf multicast-group {
      tailf:cli-embed-no-on-delete;
      tailf:cli-no-value-on-delete;
      type string;
    }
    leaf qos {
      tailf:info
        "Apply egress qos policy";
      tailf:cli-embed-no-on-delete;
      tailf:cli-no-value-on-delete;
      type uint16;
      // NCS drop tailf-common:non-strict-leafref statement
    }
    leaf scheduler-policy {
      tailf:info
        "Specify a scheduler policy";
      tailf:cli-embed-no-on-delete;
      tailf:cli-no-value-on-delete;
      tailf:cli-diff-dependency "../../multi-service-site" {
        tailf:xpath-root 3;
        tailf:cli-trigger-on-set;
      }
      // NCS drop tailf-common:non-strict-leafref statement
      type string;
    }
    container scheduler-override {
      tailf:info
        "Apply a scheduler override";
      tailf:cli-add-mode;
      leaf scheduler {
        tailf:cli-embed-no-on-delete;
        tailf:cli-no-value-on-delete;
        // NCS drop tailf-common:non-strict-leafref statement
        type string;
      }
    }
    leaf qinq-mark-top-only {
      tailf:info
        "Mark p-bits on top q-tag only";
      type empty;
    }
  }

  grouping ncs_rpc_notif_sap-ingress-grouping {
    container filter {
      tailf:cli-embed-no-on-delete;
      uses ncs_rpc_notif_filter-choice;
    }
    leaf match-qinq-dot1p {
      tailf:info
        "Define 802.1P bits to match in QinQ SAP's";
      tailf:cli-embed-no-on-delete;
      tailf:cli-no-value-on-delete;
      type enumeration {
        enum "top";
        enum "bottom";
      }
    }
    leaf qos {
      tailf:info
        "Apply ingress qos policy";
      tailf:cli-embed-no-on-delete;
      tailf:cli-no-value-on-delete;
      type uint16;
      // NCS drop tailf-common:non-strict-leafref statement
    }
    leaf scheduler-policy {
      tailf:info
        "Specify a scheduler-policy";
      tailf:cli-embed-no-on-delete;
      tailf:cli-no-value-on-delete;
      // NCS drop tailf-common:non-strict-leafref statement
      type string;
    }
    container scheduler-override {
      tailf:info
        "Apply a scheduler override";
      tailf:cli-add-mode;
      leaf scheduler {
        tailf:cli-embed-no-on-delete;
        tailf:cli-no-value-on-delete;
        // NCS drop tailf-common:non-strict-leafref statement
        type string;
      }
    }
    leaf vlan-translation {
      tailf:info
        "Apply Ingress Vlan Translation";
      tailf:cli-embed-no-on-delete;
      tailf:cli-no-value-on-delete;
      type union {
        type enumeration {
          enum "copy-outer";
        }
        type uint16 {
          range "0..4094";
        }
      }
    }
  }

  grouping ncs_rpc_notif_policy-options-action-grouping {
    choice action {
      leaf reject {
        tailf:cli-no-name-on-delete;
        type empty;
      }
      container other {
        tailf:cli-add-mode;
        tailf:cli-drop-node-name;
        tailf:cli-sequence-commands;
        leaf action {
          tailf:cli-hide-in-submode;
          tailf:cli-drop-node-name;
          type enumeration {
            enum "accept";
            enum "next-entry";
            enum "next-policy";
          }
        }
        leaf aigp-metric {
          tailf:info
            "Assign a BGP AIGP metric to routes matching the entry";
          tailf:cli-no-value-on-delete;
          tailf:cli-break-sequence-commands;
          type uint32 {
            range "0..4294967295";
          }
        }
        container as-path {
          tailf:info
            "Assign a BGP AS Path list to routes that do not match";
          tailf:cli-embed-no-on-delete;
          tailf:cli-compact-syntax;
          tailf:cli-sequence-commands;
          leaf action {
            tailf:cli-drop-node-name;
            tailf:cli-no-value-on-delete;
            type enumeration {
              enum "add";
              enum "replace";
            }
          }
          leaf name {
            tailf:cli-drop-node-name;
            tailf:cli-no-value-on-delete;
            type string {
              length "1..32";
            }
          }
        }
        container as-path-prepend {
          tailf:info
            "Prepending a BGP AS number to the AS Path attribute
                     of routes that do not match any entry";
          tailf:cli-embed-no-on-delete;
          tailf:cli-compact-syntax;
          tailf:cli-sequence-commands;
          leaf as-number {
            tailf:cli-drop-node-name;
            tailf:cli-no-value-on-delete;
            type uint32 {
              range "1..4294967295";
            }
          }
          leaf repeat {
            tailf:cli-drop-node-name;
            tailf:cli-no-value-on-delete;
            type uint8 {
              range "1..50";
            }
          }
        }
        container community {
          tailf:info
            "Apply a BGP community list to routes that do not match
                     any entry";
          tailf:cli-embed-no-on-delete;
          tailf:cli-compact-syntax;
          tailf:cli-sequence-commands;
          leaf action {
            tailf:cli-drop-node-name;
            tailf:cli-no-value-on-delete;
            type enumeration {
              enum "add";
              enum "remove";
              enum "replace";
            }
          }
          leaf name {
            tailf:cli-drop-node-name;
            tailf:cli-no-value-on-delete;
            type string {
              length "1..32";
            }
          }
        }
        container damping {
          tailf:info
            "Configure a damping profile to be used for routes that
                     do not match any entry";
          choice damping {
            leaf none {
              tailf:cli-no-name-on-delete;
              type empty;
            }
            leaf name {
              tailf:cli-drop-node-name;
              tailf:cli-no-value-on-delete;
              // NCS drop tailf-common:non-strict-leafref statement
              type string;
            }
          }
        }
        leaf local-preference {
          tailf:info
            "Assign a BGP Local Preference to routes that do not
                     match any entry";
          tailf:cli-no-value-on-delete;
          type uint32 {
            range "0..4294967295";
          }
        }
        container metric {
          tailf:info
            "Assign a metric to routes that do not match any entry";
          tailf:cli-embed-no-on-delete;
          tailf:cli-compact-syntax;
          tailf:cli-sequence-commands;
          leaf action {
            tailf:cli-drop-node-name;
            tailf:cli-no-value-on-delete;
            tailf:cli-incomplete-command;
            type enumeration {
              enum "add";
              enum "set";
              enum "subtract";
            }
          }
          leaf metric {
            tailf:cli-drop-node-name;
            tailf:cli-no-value-on-delete;
            type union {
              type enumeration {
                enum "igp";
              }
              type uint32 {
                range "0..4294967295";
              }
            }
          }
        }
        container multicast-redirect {
          tailf:info
            "Configure the interface where to redirect IGMP
                     multicast traffic to";
          tailf:cli-embed-no-on-delete;
          tailf:cli-compact-syntax;
          tailf:cli-sequence-commands;
          leaf fwd-service {
            tailf:cli-no-name-on-delete;
            tailf:cli-no-value-on-delete;
            type uint32 {
              range "1..2147483650";
            }
          }
          leaf ip-int-name {
            tailf:cli-drop-node-name;
            tailf:cli-no-value-on-delete;
            type string {
              length "1..32";
            }
          }
        }
        leaf next-hop {
          tailf:info
            "Assign a next hop IP address to routes that do not
                     match any entry";
          tailf:cli-no-value-on-delete;
          type inet:ipv4-address;
        }
        leaf next-hop-self {
          tailf:info
            "Advertising a next hop IP address belonging to this
                     router to routes that do not match any entry";
          type empty;
        }
        leaf origin {
          tailf:info
            "Set the BGP origin assigned to routes exported into
                     BGP that do not match any entry";
          tailf:cli-no-value-on-delete;
          type enumeration {
            enum "igp";
            enum "egp";
            enum "incomplete";
          }
        }
        leaf preference {
          tailf:info
            "Assign a route preference to routes that do not
                     match any entry";
          tailf:cli-no-value-on-delete;
          type uint8 {
            range "1..255";
          }
        }
        leaf tag {
          tailf:info
            "Assign an OSPF RIP or ISIS tag to routes that do
                     not match any entry";
          tailf:cli-no-value-on-delete;
          type string;
        }
        leaf type {
          tailf:info
            "Assign an OSPF type metric to routes that do not
                     match any entry";
          tailf:cli-no-value-on-delete;
          type uint8 {
            range "1..2";
          }
        }
      }
    }
  }

  grouping ncs_rpc_notif_queue-group-template-entry {
    leaf queue-group-name {
      type string;
    }
    leaf description {
      tailf:info
        "Configure description for the QoS queue-group";
      type string;
    }
    list fc {
      tailf:info
        "Configure forwarding-class to queue mappings";
      tailf:cli-embed-no-on-delete;
      key "fc-name";
      leaf fc-name {
        type enumeration {
          enum "be";
          enum "l2";
          enum "af";
          enum "l1";
          enum "h2";
          enum "ef";
          enum "h1";
          enum "nc";
        }
      }
      leaf queue {
        tailf:info
          "Specify the unicast-queue";
        tailf:cli-no-value-on-delete;
        tailf:non-strict-leafref {
          path "../../queue/queue-id";
        }
        type uint8;
      }
    }
    list policer {
      tailf:info
        "Configure QoS queue-group policer";
      key "policer-id";
      leaf policer-id {
        type uint8 {
          range "1..8";
        }
      }
      container adaptation-rule {
        tailf:info
          "Specify the CIR and PIR adaptation rules";
        tailf:cli-embed-no-on-delete;
        tailf:cli-compact-syntax;
        leaf pir {
          tailf:info
            "<pir adaption-rule>";
          tailf:cli-no-name-on-delete;
          tailf:cli-no-value-on-delete;
          type enumeration {
            enum "max";
            enum "min";
            enum "closest";
          }
        }
        leaf cir {
          tailf:info
            "<cir adaption-rule>";
          tailf:cli-no-name-on-delete;
          tailf:cli-no-value-on-delete;
          type enumeration {
            enum "max";
            enum "min";
            enum "closest";
          }
        }
      }
      leaf adv-config-policy {
        tailf:info
          "Configure advanced configuration policy";
        tailf:cli-no-value-on-delete;
        type string {
          length "1..32";
        }
      }
      container cbs {
        tailf:info
          "Specify CBS";
        tailf:cli-embed-no-on-delete;
        tailf:cli-compact-syntax;
        tailf:cli-sequence-commands;
        leaf size {
          tailf:cli-drop-node-name;
          tailf:cli-no-value-on-delete;
          type union {
            type uint32 {
              range "0..4194304";
            }
            type enumeration {
              enum "default";
            }
          }
        }
        leaf unit {
          tailf:cli-drop-node-name;
          tailf:cli-no-value-on-delete;
          type enumeration {
            enum "bytes";
            enum "kilobytes";
          }
        }
      }
      leaf description {
        tailf:info
          "Configure description for the QoS queue-group policer";
        tailf:cli-no-value-on-delete;
        type string;
      }
      leaf high-prio-only {
        tailf:info
          "Specify high priority only percent-of-mbs";
        tailf:cli-no-value-on-delete;
        type union {
          type uint8 {
            range "0..100";
          }
          type enumeration {
            enum "default";
          }
        }
      }
      container mbs {
        tailf:info
          "Specify MBS";
        tailf:cli-embed-no-on-delete;
        tailf:cli-compact-syntax;
        tailf:cli-sequence-commands;
        leaf size {
          tailf:cli-drop-node-name;
          tailf:cli-no-value-on-delete;
          type union {
            type uint32 {
              range "0..4194304";
            }
            type enumeration {
              enum "default";
            }
          }
        }
        leaf unit {
          tailf:cli-drop-node-name;
          tailf:cli-no-value-on-delete;
          type enumeration {
            enum "bytes";
            enum "kilobytes";
          }
        }
      }
      container packet-byte-offset {
        tailf:info
          "Specify packet byte offset";
        tailf:cli-embed-no-on-delete;
        tailf:cli-compact-syntax;
        choice add-delete {
          leaf add {
            tailf:cli-no-name-on-delete;
            tailf:cli-no-value-on-delete;
            type uint8 {
              range "0..31";
            }
          }
          leaf subtract {
            tailf:cli-no-name-on-delete;
            tailf:cli-no-value-on-delete;
            type uint8 {
              range "1..32";
            }
          }
        }
      }
      container parent {
        tailf:info
          "Specify the scheduler to which this policer feeds";
        tailf:cli-embed-no-on-delete;
        tailf:cli-compact-syntax;
        tailf:cli-sequence-commands;
        leaf name {
          tailf:cli-drop-node-name;
          tailf:cli-no-value-on-delete;
          type union {
            type string;
            type enumeration {
              enum "root";
            }
          }
        }
        leaf level {
          tailf:cli-no-name-on-delete;
          tailf:cli-no-value-on-delete;
          type uint8 {
            range "1..8";
          }
        }
        leaf weight-level {
          tailf:cli-no-name-on-delete;
          tailf:cli-no-value-on-delete;
          type uint8 {
            range "1..100";
          }
        }
      }
      leaf profile-capped {
        tailf:info
          "Configure Profile Cap";
        type empty;
      }
      container rate {
        tailf:info
          "Specify rates (CIR and PIR)";
        tailf:cli-embed-no-on-delete;
        tailf:cli-compact-syntax;
        tailf:cli-sequence-commands;
        leaf pir {
          tailf:cli-drop-node-name;
          tailf:cli-no-value-on-delete;
          type union {
            type uint32 {
              range "1..20000000";
            }
            type enumeration {
              enum "max";
            }
          }
        }
        leaf cir {
          tailf:cli-no-name-on-delete;
          tailf:cli-no-value-on-delete;
          type union {
            type uint32 {
              range "1..20000000";
            }
            type enumeration {
              enum "max";
            }
          }
        }
      }
      leaf stat-mode {
        tailf:info
          "Specify Stat Mode for the policer";
        tailf:cli-no-value-on-delete;
        type enumeration {
          enum "no-stats";
          enum "minimal";
          enum "offered-profile-no-cir";
          enum "offered-profile-cir";
          enum "offered-total-cir";
          enum "offered-limited-capped-cir";
          enum "offered-profile-capped-cir";
        }
      }
    }
    list queue {
      tailf:info
        "Configure a queue";
      tailf:cli-embed-no-on-delete;
      key "queue-id";
      leaf queue-id {
        type uint8 {
          range "1..8";
        }
      }
      container adaptation-rule {
        tailf:info
          "Specify the CIR and PIR adaptation rules";
        tailf:cli-embed-no-on-delete;
        tailf:cli-compact-syntax;
        leaf pir {
          tailf:info
            "<pir adaption-rule>";
          tailf:cli-no-name-on-delete;
          tailf:cli-no-value-on-delete;
          type enumeration {
            enum "max";
            enum "min";
            enum "closest";
          }
        }
        leaf cir {
          tailf:info
            "<cir adaption-rule>";
          tailf:cli-no-name-on-delete;
          tailf:cli-no-value-on-delete;
          type enumeration {
            enum "max";
            enum "min";
            enum "closest";
          }
        }
      }
      leaf adv-config-policy {
        tailf:info
          "Configure advanced configuration policy";
        tailf:cli-no-value-on-delete;
        type string {
          length "1..32";
        }
      }
      leaf burst-limit {
        tailf:info
          "Specify Burst limit";
        tailf:cli-no-value-on-delete;
        type union {
          type uint32 {
            range "1..14000000";
          }
          type enumeration {
            enum "default";
          }
        }
      }
      leaf cbs {
        tailf:info
          "Specify CBS rate";
        tailf:cli-no-value-on-delete;
        type union {
          type uint32 {
            range "0..131072";
          }
          type enumeration {
            enum "default";
          }
        }
      }
      leaf high-prio-only {
        tailf:info
          "Specify high priority only burst size";
        tailf:cli-no-value-on-delete;
        type union {
          type uint8 {
            range "0..100";
          }
        }
      }
      leaf mbs {
        tailf:info
          "Specify MBS rate";
        tailf:cli-no-value-on-delete;
        type union {
          type uint32 {
            range "0..134217728";
          }
          type enumeration {
            enum "default";
          }
        }
      }
      container parent {
        tailf:info
          "Specify the scheduler to which this queue feeds";
        tailf:cli-embed-no-on-delete;
        tailf:cli-compact-syntax;
        tailf:cli-sequence-commands;
        leaf name {
          tailf:cli-drop-node-name;
          tailf:cli-no-value-on-delete;
          type string {
            length "1..32";
          }
        }
        leaf weight {
          tailf:cli-no-name-on-delete;
          tailf:cli-no-value-on-delete;
          type uint8 {
            range "0..100";
          }
        }
        leaf level {
          tailf:cli-no-name-on-delete;
          tailf:cli-no-value-on-delete;
          type uint8 {
            range "1..8";
          }
        }
        leaf cir-weight {
          tailf:cli-no-name-on-delete;
          tailf:cli-no-value-on-delete;
          type uint8 {
            range "0..100";
          }
        }
        leaf cir-level {
          tailf:cli-no-name-on-delete;
          tailf:cli-no-value-on-delete;
          type uint8 {
            range "0..8";
          }
        }
      }
      container percent-rate {
        tailf:info
          "Specify Percent rates (CIR and PIR)";
        tailf:cli-embed-no-on-delete;
        tailf:cli-compact-syntax;
        tailf:cli-sequence-commands;
        leaf pir-percent {
          tailf:cli-drop-node-name;
          tailf:cli-no-value-on-delete;
          type decimal64 {
            fraction-digits 2;
            range "0.01..100.00";
          }
        }
        leaf cir {
          tailf:cli-no-name-on-delete;
          tailf:cli-no-value-on-delete;
          type decimal64 {
            fraction-digits 2;
            range "0.00..100.00";
          }
        }
      }
      leaf pool {
        tailf:info
          "Configure named pool for this queue";
        tailf:cli-no-value-on-delete;
        type string;
      }
      container port-parent {
        tailf:info
          "Specify the port-scheduler to which this queue feeds";
        tailf:cli-embed-no-on-delete;
        tailf:cli-compact-syntax;
        tailf:cli-sequence-commands;
        leaf weight {
          tailf:cli-no-name-on-delete;
          tailf:cli-no-value-on-delete;
          type uint8 {
            range "0..100";
          }
        }
        leaf level {
          tailf:cli-no-name-on-delete;
          tailf:cli-no-value-on-delete;
          type uint8 {
            range "1..8";
          }
        }
        leaf cir-weight {
          tailf:cli-no-name-on-delete;
          tailf:cli-no-value-on-delete;
          type uint8 {
            range "0..100";
          }
        }
        leaf cir-level {
          tailf:cli-no-name-on-delete;
          tailf:cli-no-value-on-delete;
          type uint8 {
            range "0..8";
          }
        }
      }
      container rate {
        tailf:info
          "Specify rates (CIR and PIR)";
        tailf:cli-embed-no-on-delete;
        tailf:cli-compact-syntax;
        tailf:cli-sequence-commands;
        leaf pir {
          tailf:cli-drop-node-name;
          tailf:cli-no-value-on-delete;
          type union {
            type uint32 {
              range "1..10000000";
            }
            type enumeration {
              enum "max";
            }
          }
        }
        leaf cir {
          tailf:cli-no-name-on-delete;
          tailf:cli-no-value-on-delete;
          type union {
            type uint32 {
              range "0..10000000";
            }
            type enumeration {
              enum "max";
            }
          }
        }
      }
    }
  }

  grouping ncs_rpc_notif_dhcp-lease-time {
    leaf days {
      tailf:cli-no-name-on-delete;
      tailf:cli-no-value-on-delete;
      type uint16 {
        range "0..3650";
      }
    }
    leaf hrs {
      tailf:cli-no-name-on-delete;
      tailf:cli-no-value-on-delete;
      type uint16 {
        range "0..23";
      }
    }
    leaf min {
      tailf:cli-no-name-on-delete;
      tailf:cli-no-value-on-delete;
      type uint16 {
        range "0..59";
      }
    }
    leaf sec {
      tailf:cli-no-name-on-delete;
      tailf:cli-no-value-on-delete;
      type uint16 {
        range "0..59";
      }
    }
  }

  grouping src-dst-ip {
    leaf src-ip {
      type union {
        type inet:ipv4-prefix;
        type string;
      }
    }
    leaf dst-ip {
      type union {
        type inet:ipv4-prefix;
        type string;
      }
    }
  }

  grouping ip-address-range {
    list low-high-list {
      tailf:cli-drop-node-name;
      tailf:cli-suppress-mode;
      tailf:cli-delete-when-empty;
      key "low high";
      leaf low {
        type inet:ipv4-address {
          tailf:info
            "<start-ip-address>";
        }
      }
      leaf high {
        type inet:ipv4-address {
          tailf:info
            "<stop-ip-address>";
        }
      }
    }
  }

  grouping eth-cfm {
    list mep {
      tailf:info
        "Configure a CFM Virtual Maintenance Endpoint";
      tailf:cli-embed-no-on-delete;
      tailf:cli-sequence-commands;
      key "mep-id";
      leaf mep-id {
        tailf:info
          "mep-id;;<1..8191>";
        mandatory true;
        type uint16 {
          range "1..8191";
        }
      }
      leaf domain {
        tailf:cli-hide-in-submode;
        tailf:info
          "md-index;;<1..4294967295>";
        type leafref {
          path "/ncs:devices/ncs:device/ncs:config/alu:eth-cfm/domain/id" {
            tailf:xpath-root 3;
          }
        }
        mandatory true;
      }
      leaf association {
        tailf:cli-hide-in-submode;
        tailf:info
          "ma-index;;<1..4294967295>";
        type leafref {
          path "/ncs:devices/ncs:device/ncs:config/alu:eth-cfm/domain/association/ma-index" {
            tailf:xpath-root 3;
          }
        }
        mandatory true;
      }
      leaf direction {
        tailf:info
          "<up | down>";
        tailf:cli-hide-in-submode;
        tailf:cli-no-name-on-delete;
        tailf:cli-no-value-on-delete;
        type direction;
      }
      container ais-enable {
        tailf:cli-add-mode;
        tailf:cli-embed-no-on-delete;
        tailf:cli-break-sequence-commands;
        leaf-list client-meg-level {
          tailf:cli-flat-list-syntax;
          tailf:cli-no-value-on-delete;
          type uint8 {
            range "1..7";
          }
        }
        leaf description {
          tailf:cli-embed-no-on-delete;
          type string;
        }
        leaf interval {
          tailf:cli-embed-no-on-delete;
          type enumeration {
            enum "1";
            enum "60";
          }
        }
        leaf priority {
          tailf:cli-embed-no-on-delete;
          type uint8 {
            range "0..7";
          }
        }
      }
      leaf ccm-enable {
        tailf:info
          "Enable/Disable Generation of CCM messages";
        tailf:cli-embed-no-on-delete;
        type empty;
      }
      leaf ccm-ltm-priority {
        tailf:info
          "Configure the priority of CCM and LTM messages";
        tailf:cli-embed-no-on-delete;
        type uint8 {
          range "0..7";
        }
      }
      leaf ccm-padding-size {
        tailf:info
          "Insert additional padding in the CCM packets";
        tailf:cli-embed-no-on-delete;
        type uint32;
      }
      leaf description {
        tailf:info
          "Add/remove a text description for the MEP";
        tailf:cli-embed-no-on-delete;
        type string;
      }
      container eth-test-enable {
        tailf:info
          "Enable/Disable eth-test functionality on MEP";
        tailf:cli-add-mode;
        tailf:cli-embed-no-on-delete;
        uses eth-test;
      }
      leaf fault-propagation-enable {
        tailf:info
          "Configure the Fault Propagation for the MEP";
        tailf:cli-embed-no-on-delete;
        type enumeration {
          enum "use-if-tlv";
          enum "suspend-ccm";
        }
      }
      leaf low-priority-defect {
        tailf:info
          "Configure the Lowest Priority Defect for the MEP";
        type enumeration {
          enum "allDef";
          enum "macRemErrXcon";
          enum "remErrXcon";
          enum "errXcon";
          enum "Xcon";
          enum "noXcon";
        }
      }
      leaf mac-address {
        tailf:info
          "Configure the MAC Address for the MEP";
        tailf:cli-embed-no-on-delete;
        type ieee-mac;
      }
      leaf one-way-delay-threshold {
        tailf:info
          "Configure the one-way-delay test threshold";
        type uint16 {
          range "0..600";
        }
      }
      leaf shutdown {
        tailf:info
          "Administratively enable/disable the MEP";
        tailf:cli-boolean-no;
        default "true";
        type boolean;
      }
    }
  }

  grouping igmp-snooping {
    leaf disable-router-alert {
      tailf:cli-embed-no-on-delete;
      type empty;
    }
    leaf fast-leave {
      tailf:cli-embed-no-on-delete;
      type empty;
    }
    leaf import {
      tailf:cli-embed-no-on-delete;
      type string {
        length "1..32";
      }
    }
    leaf last-member-query-interval {
      tailf:cli-embed-no-on-delete;
      type uint8 {
        range "1..50";
      }
    }
    leaf max-num-groups {
      tailf:cli-embed-no-on-delete;
      type uint16 {
        range "1..1000";
      }
    }
    leaf mrouter-port {
      tailf:cli-embed-no-on-delete;
      type empty;
    }
    leaf query-interval {
      tailf:info
        "Configure the IGMP Query Interval for v1/v2 Queriers";
      tailf:cli-embed-no-on-delete;
      type uint16 {
        range "2..1024";
      }
    }
    leaf query-response-interval {
      tailf:cli-embed-no-on-delete;
      type uint16 {
        range "1..1023";
      }
    }
    leaf robust-count {
      tailf:cli-embed-no-on-delete;
      type uint8 {
        range "1..255";
      }
    }
    leaf send-queries {
      tailf:cli-embed-no-on-delete;
      type empty;
    }
    container static {
      tailf:cli-add-mode;
      list group {
        tailf:cli-embed-no-on-delete;
        max-elements 1;
        key "group-address";
        leaf group-address {
          tailf:cli-hide-in-submode;
          type inet:ip-address;
        }
        leaf stdarg {
          tailf:cli-embed-no-on-delete;
          type string;
        }
      }
    }
    leaf version {
      tailf:cli-embed-no-on-delete;
      type uint8;
    }
  }

  grouping sdp-common {
    leaf sdp-id {
      tailf:non-strict-leafref {
        path "/ncs:devices/ncs:device/ncs:config/alu:service/sdp/sdp-id" {
          tailf:xpath-root 3;
        }
      }
      type uint32;
    }
    leaf vc-id {
      type uint32;
    }
    leaf vc-type {
      tailf:cli-hide-in-submode;
      tailf:cli-no-name-on-delete;
      tailf:cli-no-value-on-delete;
      type enumeration {
        enum "ether";
        enum "vlan";
      }
    }
    leaf endpoint {
      tailf:cli-hide-in-submode;
      tailf:cli-no-name-on-delete;
      tailf:cli-no-value-on-delete;
      tailf:non-strict-leafref {
        path "/ncs:devices/ncs:device/ncs:config/alu:service/epipe/endpoint/endpoint-name" {
          tailf:xpath-root 3;
        }
      }
      type string;
    }
    leaf shutdown {
      tailf:cli-boolean-no;
      default "false";
      type boolean;
    }
  }

  grouping sdp-spoke-mesh-common {
    uses sdp-common;
    leaf accounting-policy {
      tailf:info
        "Configure accounting-policy to be used";
      tailf:cli-no-value-on-delete;
      type uint8 {
        range "1..99";
      }
    }
    leaf auto-learn-mac-protect {
      tailf:info
        "Enable/disable automatic update of MAC protect list";
      tailf:cli-embed-no-on-delete;
      type empty;
    }
    leaf collect-stats {
      tailf:info
        "Enable/disable statistics collection";
      tailf:cli-embed-no-on-delete;
      type empty;
    }
    container egress {
      tailf:info
        "SDP binding egress configuration";
      tailf:cli-add-mode;
      container filter {
        tailf:info
          "Apply egress filter";
        tailf:cli-embed-no-on-delete;
        uses filter-choice;
      }
      container qos {
        tailf:info
          "Configure egress qos";
        tailf:cli-embed-no-on-delete;
        tailf:cli-sequence-commands;
        tailf:cli-compact-syntax;
        leaf network-policy-id {
          tailf:info
            "<network-policy-id>";
          tailf:cli-drop-node-name;
          tailf:cli-no-value-on-delete;
          type uint16;
          tailf:non-strict-leafref {
            path "/ncs:devices/ncs:device/ncs:config/alu:qos/sap-egress/policy-id" {
              tailf:xpath-root 3;
            }
          }
        }
        leaf port-redirect-group {
          tailf:info
            "<queue-group-name>";
          tailf:cli-no-name-on-delete;
          tailf:cli-no-value-on-delete;
          tailf:non-strict-leafref {
            path "/ncs:devices/ncs:device/ncs:config/alu:qos/queue-group-templates/egress/queue-group/queue-group-name" {
              tailf:xpath-root 3;
            }
          }
          type string;
        }
        leaf instance {
          tailf:info
            "<instance-id>";
          tailf:cli-no-name-on-delete;
          tailf:cli-no-value-on-delete;
          type uint16 {
            range "1..16384";
          }
        }
      }
      leaf vc-label {
        tailf:info
          "Configure egress label";
        type uint32 {
          range "16..1048575";
        }
      }
    }
    container eth-cfm {
      tailf:info
        "Configure CFM parameters";
      tailf:cli-add-mode;
      uses eth-cfm;
    }
    leaf force-vlan-forwarding {
      tailf:info
        "Forces vlan-vc-type forwarding in the data-path";
      type empty;
    }
    container igmp-snooping {
      tailf:info
        "Configure IGMP snooping parameters";
      uses igmp-snooping;
    }
    container ingress {
      tailf:info
        "SDP binding ingress configuration";
      tailf:cli-add-mode;
      container filter {
        tailf:info
          "Apply ingress filter";
        tailf:cli-embed-no-on-delete;
        uses filter-choice;
      }
      container qos {
        tailf:info
          "Configure egress qos";
        tailf:cli-embed-no-on-delete;
        tailf:cli-sequence-commands;
        tailf:cli-compact-syntax;
        leaf network-policy-id {
          tailf:info
            "<network-policy-id>";
          tailf:cli-drop-node-name;
          tailf:cli-no-value-on-delete;
          type uint16;
          tailf:non-strict-leafref {
            path "/ncs:devices/ncs:device/ncs:config/alu:qos/sap-ingress/policy-id" {
              tailf:xpath-root 3;
            }
          }
        }
        leaf fp-redirect-group {
          tailf:info
            "<queue-group-name>";
          tailf:cli-no-name-on-delete;
          tailf:cli-no-value-on-delete;
          tailf:non-strict-leafref {
            path "/ncs:devices/ncs:device/ncs:config/alu:qos/queue-group-templates/ingress/queue-group/queue-group-name" {
              tailf:xpath-root 3;
            }
          }
          type string;
        }
        leaf instance {
          tailf:info
            "<instance-id>";
          tailf:cli-no-name-on-delete;
          tailf:cli-no-value-on-delete;
          type uint16 {
            range "1..16384";
          }
        }
      }
      leaf vc-label {
        tailf:info
          "Configure egress label";
        type uint32 {
          range "16..1048575";
        }
      }
    }
    leaf mac-pinning {
      tailf:info
        "Enable/disable MAC address pinning";
      type empty;
    }
    list static-mac {
      tailf:info
        "Configure a static mac entry";
      tailf:cli-embed-no-on-delete;
      tailf:cli-suppress-mode;
      key "address";
      leaf address {
        type ieee-mac;
      }
    }
    leaf restrict-protected-src {
      tailf:info
        "Enable/disable protected src MAC restriction";
      tailf:cli-no-value-on-delete;
      type enumeration {
        enum "alarm-only";
        enum "discard-frame";
      }
    }
    leaf vlan-vc-tag {
      type uint16 {
        range "0..4094";
      }
    }
  }

  grouping stp-common {
    leaf auto-edge {
      tailf:info
        "Enable/disable automatic detection of edge port";
      tailf:cli-embed-no-on-delete;
      type empty;
    }
    leaf edge-port {
      tailf:info
        "Configure spoke-sdp as edge port";
      tailf:cli-embed-no-on-delete;
      type empty;
    }
    leaf link-type {
      tailf:info
        "Configure link type of the spoke-sdp";
      tailf:cli-embed-no-on-delete;
      type enumeration {
        enum "pt-pt";
        enum "shared";
      }
    }
    leaf path-cost {
      tailf:info
        "Configure path-cost";
      tailf:cli-no-name-on-delete;
      type uint32 {
        range "1..200000000";
      }
    }
    leaf port-num {
      tailf:info
        "Configure virtual port number";
      tailf:cli-embed-no-on-delete;
      type uint16;
    }
    leaf priority {
      tailf:info
        "Configure stp priority";
      tailf:cli-embed-no-on-delete;
      type uint16 {
        range "4096..65535";
      }
    }
    leaf shutdown {
      tailf:info
        "Enable/disable spanning tree protocol";
      tailf:cli-boolean-no;
      default "true";
      type boolean;
    }
  }

  grouping filter-choice {
    choice filter {
      leaf ip {
        tailf:info
          "<ip-filter-id>;;[1..65535]|<name:64 char max>";
        tailf:non-strict-leafref {
          path "/ncs:devices/ncs:device/ncs:config/alu:filter/ip-filter/ip-filter-name" {
            tailf:xpath-root 3;
          }
        }
        type string;
      }
      leaf ipv6 {
        tailf:info
          "<ipv6-filter-id>;;[1..65535]|<name:64 char max>";
        tailf:non-strict-leafref {
          path "/ncs:devices/ncs:device/ncs:config/alu:filter/ipv6-filter/ip-filter-name" {
            tailf:xpath-root 3;
          }
        }
        type string;
      }
      leaf mac {
        tailf:info
          "<mac-filter-id>;;[1..65535]|<name:64 char max>";
        tailf:non-strict-leafref {
          path "/ncs:devices/ncs:device/ncs:config/alu:filter/mac-filter/mac-filter-name" {
            tailf:xpath-root 3;
          }
        }
        type string;
      }
    }
  }

  grouping eth-test {
    leaf test-pattern {
      tailf:cli-embed-no-on-delete;
      type test-pattern;
    }
    leaf crc-enable {
      type empty;
      when '../test-pattern' {
        tailf:xpath-root 3;
      }
    }
  }

  grouping time-stamp {
    leaf start-week {
      tailf:cli-drop-node-name;
      type enumeration {
        enum "first";
        enum "second";
        enum "third";
        enum "fourth";
        enum "last";
      }
    }
    leaf start-day {
      tailf:cli-drop-node-name;
      type enumeration {
        enum "sunday";
        enum "monday";
        enum "tuesday";
        enum "wednesday";
        enum "thursday";
        enum "friday";
        enum "saturday";
      }
    }
    leaf month {
      tailf:cli-drop-node-name;
      type enumeration {
        enum "january";
        enum "february";
        enum "march";
        enum "april";
        enum "may";
        enum "june";
        enum "july";
        enum "august";
        enum "september";
        enum "october";
        enum "november";
        enum "december";
      }
    }
    leaf hours-minutes {
      tailf:cli-drop-node-name;
      type string;
    }
  }

  grouping ip-filter-entry-grouping {
    leaf entry-name {
      type string;
    }
    leaf description {
      tailf:cli-no-name-on-delete;
      type string {
        length "1..80";
      }
    }
    leaf log {
      tailf:cli-embed-no-on-delete;
      type uint16;
    }
    container match {
      tailf:cli-add-mode;
      leaf protocol {
        tailf:cli-hide-in-submode;
        type protocol;
      }
      leaf dscp {
        type dscp-type;
      }
      container src-ip {
        tailf:cli-embed-no-on-delete;
        tailf:cli-compact-syntax;
        tailf:cli-sequence-commands;
        uses filter-match-ip-grouping;
      }
      container dst-ip {
        tailf:cli-embed-no-on-delete;
        tailf:cli-compact-syntax;
        tailf:cli-sequence-commands;
        uses filter-match-ip-grouping;
      }
      leaf icmp-type {
        type icmp-type;
      }
      leaf icmp-code {
        type uint32;
      }
      leaf fragment {
        type boolean;
      }
      container ip-option {
        tailf:cli-compact-syntax;
        leaf a {
          tailf:cli-drop-node-name;
          type uint32;
        }
        leaf b {
          tailf:cli-drop-node-name;
          type uint32;
        }
      }
      container dst-port {
        tailf:cli-compact-syntax;
        tailf:cli-sequence-commands;
        tailf:cli-embed-no-on-delete;
        choice port-choice {
          case a {
            leaf op {
              tailf:info
                "operators";
              tailf:cli-drop-node-name;
              tailf:cli-no-value-on-delete;
              type enumeration {
                enum "lt";
                enum "gt";
                enum "eq";
              }
            }
            leaf port {
              tailf:info
                "port number";
              tailf:cli-drop-node-name;
              tailf:cli-no-value-on-delete;
              mandatory true;
              type uint16;
            }
          }
          case b {
            leaf range {
              tailf:info
                "port range";
              type empty;
            }
            leaf start {
              tailf:info
                "start";
              tailf:cli-drop-node-name;
              tailf:cli-no-value-on-delete;
              mandatory true;
              type uint16;
            }
            leaf end {
              tailf:info
                "end";
              tailf:cli-drop-node-name;
              tailf:cli-no-value-on-delete;
              mandatory true;
              type uint16;
            }
          }
        }
      }
      container src-port {
        tailf:cli-compact-syntax;
        tailf:cli-sequence-commands;
        tailf:cli-embed-no-on-delete;
        choice port-choice {
          case a {
            leaf op {
              tailf:cli-drop-node-name;
              tailf:cli-no-value-on-delete;
              type enumeration {
                enum "lt";
                enum "gt";
                enum "eq";
              }
            }
            leaf port {
              tailf:cli-drop-node-name;
              tailf:cli-no-value-on-delete;
              mandatory true;
              type uint16;
            }
          }
          case b {
            leaf range {
              type empty;
            }
            leaf start {
              tailf:cli-drop-node-name;
              tailf:cli-no-value-on-delete;
              mandatory true;
              type uint16;
            }
            leaf end {
              tailf:cli-drop-node-name;
              tailf:cli-no-value-on-delete;
              mandatory true;
              type uint16;
            }
          }
          case c {
            leaf src-port-number {
              tailf:cli-drop-node-name;
              type uint16;
            }
            leaf mask {
              tailf:cli-drop-node-name;
              mandatory true;
              type uint16;
            }
          }
        }
      }
    }
  }

  grouping ipv6-filter-entry-grouping {
    leaf entry-name {
      type string;
    }
    leaf description {
      type string;
    }
    container match {
      tailf:cli-add-mode;
      leaf next-header {
        tailf:cli-hide-in-submode;
        type enumeration {
          enum "*";
          enum "none";
          enum "icmp";
          enum "igmp";
          enum "ip";
          enum "tcp";
          enum "egp";
          enum "igp";
          enum "udp";
          enum "rdp";
          enum "ipv6";
          enum "idrp";
          enum "rsvp";
          enum "gre";
          enum "ipv6-icmp";
          enum "ipv6-no-nxt";
          enum "iso-ip";
          enum "eigrp";
          enum "ospf-igp";
          enum "ether-ip";
          enum "encap";
          enum "pnni";
          enum "pim";
          enum "vrrp";
          enum "l2tp";
          enum "stp";
          enum "ptp";
          enum "isis";
          enum "crtp";
          enum "crudp";
          enum "sctp";
        }
      }
      leaf dscp {
        type dscp-type;
      }
      container src-ip {
        tailf:cli-embed-no-on-delete;
        tailf:cli-compact-syntax;
        tailf:cli-sequence-commands;
        uses filter-match-ipv6-grouping;
      }
      container dst-ip {
        tailf:cli-embed-no-on-delete;
        tailf:cli-compact-syntax;
        tailf:cli-sequence-commands;
        uses filter-match-ipv6-grouping;
      }
      leaf icmp-type {
        type icmpv6-type;
      }
      leaf icmp-code {
        type uint32;
      }
      leaf fragment {
        type boolean;
      }
      container ip-option {
        tailf:cli-compact-syntax;
        leaf a {
          tailf:cli-drop-node-name;
          type uint32;
        }
        leaf b {
          tailf:cli-drop-node-name;
          type uint32;
        }
      }
      container dst-port {
        tailf:cli-compact-syntax;
        tailf:cli-sequence-commands;
        choice port-choice {
          case a {
            leaf op {
              tailf:cli-drop-node-name;
              type enumeration {
                enum "lt";
                enum "gt";
                enum "eq";
              }
            }
            leaf port {
              tailf:cli-drop-node-name;
              type uint16;
            }
          }
          case b {
            leaf range {
              type empty;
            }
            leaf start {
              tailf:cli-drop-node-name;
              type uint16;
            }
            leaf end {
              tailf:cli-drop-node-name;
              type uint16;
            }
          }
        }
      }
      container src-port {
        tailf:cli-compact-syntax;
        tailf:cli-sequence-commands;
        choice port-choice {
          case a {
            leaf op {
              tailf:cli-drop-node-name;
              type enumeration {
                enum "lt";
                enum "gt";
                enum "eq";
              }
            }
            leaf port {
              tailf:cli-drop-node-name;
              type uint16;
            }
          }
          case b {
            leaf range {
              type empty;
            }
            leaf start {
              tailf:cli-drop-node-name;
              type uint16;
            }
            leaf end {
              tailf:cli-drop-node-name;
              type uint16;
            }
          }
        }
      }
    }
  }

  grouping queue-override-grouping {
    list queue {
      tailf:cli-embed-no-on-delete;
      key "queue-id";
      leaf queue-id {
        type uint32;
      }
      container adaption-rule {
        tailf:cli-compact-syntax;
        tailf:cli-sequence-commands;
        tailf:cli-embed-no-on-delete;
        leaf pir {
          type adaption-rule;
        }
        leaf cir {
          type adaption-rule;
        }
      }
      leaf avg-frame-overhead {
        tailf:cli-embed-no-on-delete;
        type decimal64 {
          fraction-digits 2;
          range "0..100";
        }
      }
      container mbs {
        tailf:cli-compact-syntax;
        tailf:cli-sequence-commands;
        tailf:cli-embed-no-on-delete;
        leaf val {
          tailf:cli-drop-node-name;
          type union {
            type enumeration {
              enum "default";
            }
            type uint32 {
              range "0..134217728";
            }
          }
        }
        leaf unit {
          tailf:cli-drop-node-name;
          type enumeration {
            enum "bytes";
            enum "kilobytes";
          }
        }
      }
      leaf cbs {
        tailf:cli-embed-no-on-delete;
        type union {
          type enumeration {
            enum "default";
          }
          type uint32 {
            range "0..131072";
          }
        }
      }
      leaf high-prio-only {
        type union {
          type enumeration {
            enum "default";
          }
          type uint8;
        }
      }
      container rate {
        tailf:cli-compact-syntax;
        tailf:cli-sequence-commands;
        tailf:cli-embed-no-on-delete;
        leaf pir {
          tailf:cli-drop-node-name;
          type union {
            type enumeration {
              enum "max";
            }
            type uint32 {
              range "1..100000000";
            }
          }
        }
        leaf cir {
          type union {
            type enumeration {
              enum "max";
            }
            type uint32 {
              range "0..100000000";
            }
          }
        }
      }
      container parent {
        tailf:cli-compact-syntax;
        tailf:cli-sequence-commands;
        tailf:cli-embed-no-on-delete;
        leaf weight {
          type uint8 {
            range "0..100";
          }
        }
        leaf cir-weight {
          type uint8 {
            range "0..100";
          }
        }
      }
      container percent-rate {
        tailf:cli-compact-syntax;
        tailf:cli-sequence-commands;
        tailf:cli-embed-no-on-delete;
        leaf pir {
          tailf:cli-drop-node-name;
          type decimal64 {
            fraction-digits 2;
            range "0..100";
          }
        }
        leaf cir {
          type decimal64 {
            fraction-digits 2;
            range "0..100";
          }
        }
      }
    }
  }

  grouping ip-criteria-grouping {
    leaf match-criteria {
      tailf:cli-hide-in-submode;
      tailf:cli-drop-node-name;
      tailf:cli-no-value-on-delete;
      type enumeration {
        enum "any";
        enum "dscp-only";
      }
    }
    list entry {
      key "id";
      leaf id {
        type uint16;
      }
      leaf description {
        tailf:cli-embed-no-on-delete;
        type string;
      }
      container match {
        tailf:cli-add-mode;
        leaf protocol {
          tailf:cli-hide-in-submode;
          type protocol;
        }
        leaf dscp {
          type string;
        }
        leaf dst-ip {
          type tailf:ipv4-address-and-prefix-length;
        }
        leaf src-ip {
          type tailf:ipv4-address-and-prefix-length;
        }
        container dst-port {
          tailf:cli-compact-syntax;
          tailf:cli-sequence-commands;
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container src-port {
          tailf:cli-compact-syntax;
          tailf:cli-sequence-commands;
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
      }
      container action {
        tailf:cli-compact-syntax;
        leaf fc {
          type string;
        }
        leaf priority {
          type enumeration {
            enum "high";
            enum "low";
          }
        }
      }
    }
  }

  grouping ipv6-criteria-grouping {
    list entry {
      key "id";
      leaf id {
        type uint16;
      }
      leaf description {
        type string;
      }
      container match {
        tailf:cli-add-mode;
        leaf protocol {
          tailf:cli-hide-in-submode;
          type protocol;
        }
        leaf dst-ip {
          type tailf:ipv6-address-and-prefix-length;
        }
        leaf src-ip {
          type tailf:ipv6-address-and-prefix-length;
        }
        container dst-port {
          tailf:cli-compact-syntax;
          tailf:cli-sequence-commands;
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container src-port {
          tailf:cli-compact-syntax;
          tailf:cli-sequence-commands;
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
      }
      container action {
        tailf:cli-compact-syntax;
        leaf fc {
          type string;
        }
        leaf priority {
          type enumeration {
            enum "high";
            enum "low";
          }
        }
      }
    }
  }

  grouping meter-grouping {
    leaf meter-id {
      type uint8 {
        range "1..32";
      }
    }
    leaf multipoint {
      tailf:cli-hide-in-submode;
      tailf:cli-no-name-on-delete;
      type empty;
    }
    container adaptation-rule {
      tailf:info
        "Specify the CIR and PIR adaptation rules";
      tailf:cli-embed-no-on-delete;
      tailf:cli-compact-syntax;
      leaf cir {
        tailf:cli-no-name-on-delete;
        tailf:cli-no-value-on-delete;
        type enumeration {
          enum "max";
          enum "min";
          enum "closest";
        }
      }
      leaf pir {
        tailf:cli-no-name-on-delete;
        tailf:cli-no-value-on-delete;
        type enumeration {
          enum "max";
          enum "min";
          enum "closest";
        }
      }
    }
    container cbs {
      tailf:info
        "Specify CBS";
      tailf:cli-compact-syntax;
      leaf size {
        tailf:cli-drop-node-name;
        tailf:cli-no-value-on-delete;
        type union {
          type uint32 {
            range "4..2146959";
          }
          type enumeration {
            enum "default";
          }
        }
      }
    }
    container mbs {
      tailf:info
        "Specify MBS";
      tailf:cli-compact-syntax;
      leaf size {
        tailf:cli-drop-node-name;
        tailf:cli-no-value-on-delete;
        type union {
          type uint32 {
            range "4..2146959";
          }
          type enumeration {
            enum "default";
          }
        }
      }
    }
    container rate {
      tailf:info
        "Specify rates (CIR and PIR)";
      tailf:cli-compact-syntax;
      tailf:cli-embed-no-on-delete;
      leaf pir {
        tailf:cli-no-value-on-delete;
        type union {
          type uint32 {
            range "0..20000000";
          }
          type enumeration {
            enum "max";
          }
        }
      }
      leaf cir {
        tailf:cli-no-value-on-delete;
        type union {
          type uint32 {
            range "0..20000000";
          }
          type enumeration {
            enum "max";
          }
        }
      }
    }
    leaf mode {
      tailf:info
        "Specify rate mode";
      type enumeration {
        enum "trtcm1";
        enum "trtcm2";
        enum "srtcm";
      }
    }
  }

  grouping cpm-filter-match-port-grouping {
    choice port-choice {
      case a {
        leaf port-number {
          tailf:info
            "<tcp/udp port-number>";
          tailf:cli-drop-node-name;
          tailf:cli-no-value-on-delete;
          type uint16;
        }
        leaf mask {
          tailf:info
            "<tcp/udp port mask>";
          tailf:cli-drop-node-name;
          tailf:cli-no-value-on-delete;
          type uint16;
        }
      }
      case b {
        leaf range {
          tailf:info
            "range <tcp/udp port-number> <tcp/udp port-number>";
          type empty;
        }
        leaf start {
          tailf:cli-drop-node-name;
          type uint16;
        }
        leaf end {
          tailf:cli-drop-node-name;
          type uint16;
        }
      }
      case c {
        leaf port-list {
          tailf:info
            "port-list <port-list-name>";
          type string {
            length "1..32";
          }
        }
      }
    }
  }

  grouping filter-match-ip-grouping {
    choice ip {
      leaf address {
        tailf:info
          "<ip-address/prefix-length> | <ip-address>";
        tailf:cli-drop-node-name;
        tailf:cli-no-value-on-delete;
        type union {
          type inet:ipv4-address;
          type inet:ipv4-prefix;
          type string;
        }
      }
      leaf ip-prefix-list {
        tailf:info
          "ip-prefix-list <prefix-list-name>";
        tailf:cli-no-value-on-delete;
        tailf:cli-no-name-on-delete;
        type string;
      }
    }
  }

  grouping filter-match-ipv6-grouping {
    choice ipv6 {
      leaf address {
        tailf:info
          "<ipv6-address/prefix-length> | <ipv6-address>";
        tailf:cli-drop-node-name;
        tailf:cli-no-value-on-delete;
        type union {
          type tailf:ipv6-address-and-prefix-length;
          type inet:ipv6-address;
          type string;
        }
      }
      leaf ipv6-prefix-list {
        tailf:info
          "ipv6-prefix-list <prefix-list-name>";
        tailf:cli-no-value-on-delete;
        tailf:cli-no-name-on-delete;
        type string;
      }
    }
  }

  grouping sap-egress-grouping {
    leaf agg-rate-limit {
      tailf:cli-embed-no-on-delete;
      tailf:cli-no-value-on-delete;
      type uint32 {
        range "1..40000000";
      }
    }
    container filter {
      tailf:cli-embed-no-on-delete;
      uses filter-choice;
    }
    leaf multicast-group {
      tailf:cli-embed-no-on-delete;
      tailf:cli-no-value-on-delete;
      type string;
    }
    leaf qos {
      tailf:info
        "Apply egress qos policy";
      tailf:cli-embed-no-on-delete;
      tailf:cli-no-value-on-delete;
      type uint16;
      tailf:non-strict-leafref {
        path "/ncs:devices/ncs:device/ncs:config/alu:qos/sap-egress/policy-id" {
          tailf:xpath-root 3;
        }
      }
    }
    leaf scheduler-policy {
      tailf:info
        "Specify a scheduler policy";
      tailf:cli-embed-no-on-delete;
      tailf:cli-no-value-on-delete;
      tailf:cli-diff-dependency "../../multi-service-site" {
        tailf:xpath-root 3;
        tailf:cli-trigger-on-set;
      }
      tailf:non-strict-leafref {
        path "/ncs:devices/ncs:device/ncs:config/alu:qos/scheduler-policy/scheduler-policy-name" {
          tailf:xpath-root 3;
        }
      }
      type string;
    }
    container scheduler-override {
      tailf:info
        "Apply a scheduler override";
      tailf:cli-add-mode;
      leaf scheduler {
        tailf:cli-embed-no-on-delete;
        tailf:cli-no-value-on-delete;
        tailf:non-strict-leafref {
          path "/ncs:devices/ncs:device/ncs:config/alu:qos/scheduler-policy/scheduler-policy-name" {
            tailf:xpath-root 3;
          }
        }
        type string;
      }
    }
    leaf qinq-mark-top-only {
      tailf:info
        "Mark p-bits on top q-tag only";
      type empty;
    }
  }

  grouping sap-ingress-grouping {
    container filter {
      tailf:cli-embed-no-on-delete;
      uses filter-choice;
    }
    leaf match-qinq-dot1p {
      tailf:info
        "Define 802.1P bits to match in QinQ SAP's";
      tailf:cli-embed-no-on-delete;
      tailf:cli-no-value-on-delete;
      type enumeration {
        enum "top";
        enum "bottom";
      }
    }
    leaf qos {
      tailf:info
        "Apply ingress qos policy";
      tailf:cli-embed-no-on-delete;
      tailf:cli-no-value-on-delete;
      type uint16;
      tailf:non-strict-leafref {
        path "/ncs:devices/ncs:device/ncs:config/alu:qos/sap-ingress/policy-id" {
          tailf:xpath-root 3;
        }
      }
    }
    leaf scheduler-policy {
      tailf:info
        "Specify a scheduler-policy";
      tailf:cli-embed-no-on-delete;
      tailf:cli-no-value-on-delete;
      tailf:non-strict-leafref {
        path "/ncs:devices/ncs:device/ncs:config/alu:qos/scheduler-policy/scheduler-policy-name" {
          tailf:xpath-root 3;
        }
      }
      type string;
    }
    container scheduler-override {
      tailf:info
        "Apply a scheduler override";
      tailf:cli-add-mode;
      leaf scheduler {
        tailf:cli-embed-no-on-delete;
        tailf:cli-no-value-on-delete;
        tailf:non-strict-leafref {
          path "/ncs:devices/ncs:device/ncs:config/alu:qos/scheduler-policy/scheduler-policy-name" {
            tailf:xpath-root 3;
          }
        }
        type string;
      }
    }
    leaf vlan-translation {
      tailf:info
        "Apply Ingress Vlan Translation";
      tailf:cli-embed-no-on-delete;
      tailf:cli-no-value-on-delete;
      type union {
        type enumeration {
          enum "copy-outer";
        }
        type uint16 {
          range "0..4094";
        }
      }
    }
  }

  grouping policy-options-action-grouping {
    choice action {
      leaf reject {
        tailf:cli-no-name-on-delete;
        type empty;
      }
      container other {
        tailf:cli-add-mode;
        tailf:cli-drop-node-name;
        tailf:cli-sequence-commands;
        leaf action {
          tailf:cli-hide-in-submode;
          tailf:cli-drop-node-name;
          type enumeration {
            enum "accept";
            enum "next-entry";
            enum "next-policy";
          }
        }
        leaf aigp-metric {
          tailf:info
            "Assign a BGP AIGP metric to routes matching the entry";
          tailf:cli-no-value-on-delete;
          tailf:cli-break-sequence-commands;
          type uint32 {
            range "0..4294967295";
          }
        }
        container as-path {
          tailf:info
            "Assign a BGP AS Path list to routes that do not match";
          tailf:cli-embed-no-on-delete;
          tailf:cli-compact-syntax;
          tailf:cli-sequence-commands;
          leaf action {
            tailf:cli-drop-node-name;
            tailf:cli-no-value-on-delete;
            type enumeration {
              enum "add";
              enum "replace";
            }
          }
          leaf name {
            tailf:cli-drop-node-name;
            tailf:cli-no-value-on-delete;
            type string {
              length "1..32";
            }
          }
        }
        container as-path-prepend {
          tailf:info
            "Prepending a BGP AS number to the AS Path attribute
                     of routes that do not match any entry";
          tailf:cli-embed-no-on-delete;
          tailf:cli-compact-syntax;
          tailf:cli-sequence-commands;
          leaf as-number {
            tailf:cli-drop-node-name;
            tailf:cli-no-value-on-delete;
            type uint32 {
              range "1..4294967295";
            }
          }
          leaf repeat {
            tailf:cli-drop-node-name;
            tailf:cli-no-value-on-delete;
            type uint8 {
              range "1..50";
            }
          }
        }
        container community {
          tailf:info
            "Apply a BGP community list to routes that do not match
                     any entry";
          tailf:cli-embed-no-on-delete;
          tailf:cli-compact-syntax;
          tailf:cli-sequence-commands;
          leaf action {
            tailf:cli-drop-node-name;
            tailf:cli-no-value-on-delete;
            type enumeration {
              enum "add";
              enum "remove";
              enum "replace";
            }
          }
          leaf name {
            tailf:cli-drop-node-name;
            tailf:cli-no-value-on-delete;
            type string {
              length "1..32";
            }
          }
        }
        container damping {
          tailf:info
            "Configure a damping profile to be used for routes that
                     do not match any entry";
          choice damping {
            leaf none {
              tailf:cli-no-name-on-delete;
              type empty;
            }
            leaf name {
              tailf:cli-drop-node-name;
              tailf:cli-no-value-on-delete;
              tailf:non-strict-leafref {
                path "/ncs:devices/ncs:device/ncs:config/alu:router/policy-options/begin/damping/name" {
                  tailf:xpath-root 3;
                }
              }
              type string;
            }
          }
        }
        leaf local-preference {
          tailf:info
            "Assign a BGP Local Preference to routes that do not
                     match any entry";
          tailf:cli-no-value-on-delete;
          type uint32 {
            range "0..4294967295";
          }
        }
        container metric {
          tailf:info
            "Assign a metric to routes that do not match any entry";
          tailf:cli-embed-no-on-delete;
          tailf:cli-compact-syntax;
          tailf:cli-sequence-commands;
          leaf action {
            tailf:cli-drop-node-name;
            tailf:cli-no-value-on-delete;
            tailf:cli-incomplete-command;
            type enumeration {
              enum "add";
              enum "set";
              enum "subtract";
            }
          }
          leaf metric {
            tailf:cli-drop-node-name;
            tailf:cli-no-value-on-delete;
            type union {
              type enumeration {
                enum "igp";
              }
              type uint32 {
                range "0..4294967295";
              }
            }
          }
        }
        container multicast-redirect {
          tailf:info
            "Configure the interface where to redirect IGMP
                     multicast traffic to";
          tailf:cli-embed-no-on-delete;
          tailf:cli-compact-syntax;
          tailf:cli-sequence-commands;
          leaf fwd-service {
            tailf:cli-no-name-on-delete;
            tailf:cli-no-value-on-delete;
            type uint32 {
              range "1..2147483650";
            }
          }
          leaf ip-int-name {
            tailf:cli-drop-node-name;
            tailf:cli-no-value-on-delete;
            type string {
              length "1..32";
            }
          }
        }
        leaf next-hop {
          tailf:info
            "Assign a next hop IP address to routes that do not
                     match any entry";
          tailf:cli-no-value-on-delete;
          type inet:ipv4-address;
        }
        leaf next-hop-self {
          tailf:info
            "Advertising a next hop IP address belonging to this
                     router to routes that do not match any entry";
          type empty;
        }
        leaf origin {
          tailf:info
            "Set the BGP origin assigned to routes exported into
                     BGP that do not match any entry";
          tailf:cli-no-value-on-delete;
          type enumeration {
            enum "igp";
            enum "egp";
            enum "incomplete";
          }
        }
        leaf preference {
          tailf:info
            "Assign a route preference to routes that do not
                     match any entry";
          tailf:cli-no-value-on-delete;
          type uint8 {
            range "1..255";
          }
        }
        leaf tag {
          tailf:info
            "Assign an OSPF RIP or ISIS tag to routes that do
                     not match any entry";
          tailf:cli-no-value-on-delete;
          type string;
        }
        leaf type {
          tailf:info
            "Assign an OSPF type metric to routes that do not
                     match any entry";
          tailf:cli-no-value-on-delete;
          type uint8 {
            range "1..2";
          }
        }
      }
    }
  }

  grouping queue-group-template-entry {
    leaf queue-group-name {
      type string;
    }
    leaf description {
      tailf:info
        "Configure description for the QoS queue-group";
      type string;
    }
    list fc {
      tailf:info
        "Configure forwarding-class to queue mappings";
      tailf:cli-embed-no-on-delete;
      key "fc-name";
      leaf fc-name {
        type enumeration {
          enum "be";
          enum "l2";
          enum "af";
          enum "l1";
          enum "h2";
          enum "ef";
          enum "h1";
          enum "nc";
        }
      }
      leaf queue {
        tailf:info
          "Specify the unicast-queue";
        tailf:cli-no-value-on-delete;
        tailf:non-strict-leafref {
          path "../../queue/queue-id";
        }
        type uint8;
      }
    }
    list policer {
      tailf:info
        "Configure QoS queue-group policer";
      key "policer-id";
      leaf policer-id {
        type uint8 {
          range "1..8";
        }
      }
      container adaptation-rule {
        tailf:info
          "Specify the CIR and PIR adaptation rules";
        tailf:cli-embed-no-on-delete;
        tailf:cli-compact-syntax;
        leaf pir {
          tailf:info
            "<pir adaption-rule>";
          tailf:cli-no-name-on-delete;
          tailf:cli-no-value-on-delete;
          type enumeration {
            enum "max";
            enum "min";
            enum "closest";
          }
        }
        leaf cir {
          tailf:info
            "<cir adaption-rule>";
          tailf:cli-no-name-on-delete;
          tailf:cli-no-value-on-delete;
          type enumeration {
            enum "max";
            enum "min";
            enum "closest";
          }
        }
      }
      leaf adv-config-policy {
        tailf:info
          "Configure advanced configuration policy";
        tailf:cli-no-value-on-delete;
        type string {
          length "1..32";
        }
      }
      container cbs {
        tailf:info
          "Specify CBS";
        tailf:cli-embed-no-on-delete;
        tailf:cli-compact-syntax;
        tailf:cli-sequence-commands;
        leaf size {
          tailf:cli-drop-node-name;
          tailf:cli-no-value-on-delete;
          type union {
            type uint32 {
              range "0..4194304";
            }
            type enumeration {
              enum "default";
            }
          }
        }
        leaf unit {
          tailf:cli-drop-node-name;
          tailf:cli-no-value-on-delete;
          type enumeration {
            enum "bytes";
            enum "kilobytes";
          }
        }
      }
      leaf description {
        tailf:info
          "Configure description for the QoS queue-group policer";
        tailf:cli-no-value-on-delete;
        type string;
      }
      leaf high-prio-only {
        tailf:info
          "Specify high priority only percent-of-mbs";
        tailf:cli-no-value-on-delete;
        type union {
          type uint8 {
            range "0..100";
          }
          type enumeration {
            enum "default";
          }
        }
      }
      container mbs {
        tailf:info
          "Specify MBS";
        tailf:cli-embed-no-on-delete;
        tailf:cli-compact-syntax;
        tailf:cli-sequence-commands;
        leaf size {
          tailf:cli-drop-node-name;
          tailf:cli-no-value-on-delete;
          type union {
            type uint32 {
              range "0..4194304";
            }
            type enumeration {
              enum "default";
            }
          }
        }
        leaf unit {
          tailf:cli-drop-node-name;
          tailf:cli-no-value-on-delete;
          type enumeration {
            enum "bytes";
            enum "kilobytes";
          }
        }
      }
      container packet-byte-offset {
        tailf:info
          "Specify packet byte offset";
        tailf:cli-embed-no-on-delete;
        tailf:cli-compact-syntax;
        choice add-delete {
          leaf add {
            tailf:cli-no-name-on-delete;
            tailf:cli-no-value-on-delete;
            type uint8 {
              range "0..31";
            }
          }
          leaf subtract {
            tailf:cli-no-name-on-delete;
            tailf:cli-no-value-on-delete;
            type uint8 {
              range "1..32";
            }
          }
        }
      }
      container parent {
        tailf:info
          "Specify the scheduler to which this policer feeds";
        tailf:cli-embed-no-on-delete;
        tailf:cli-compact-syntax;
        tailf:cli-sequence-commands;
        leaf name {
          tailf:cli-drop-node-name;
          tailf:cli-no-value-on-delete;
          type union {
            type string;
            type enumeration {
              enum "root";
            }
          }
        }
        leaf level {
          tailf:cli-no-name-on-delete;
          tailf:cli-no-value-on-delete;
          type uint8 {
            range "1..8";
          }
        }
        leaf weight-level {
          tailf:cli-no-name-on-delete;
          tailf:cli-no-value-on-delete;
          type uint8 {
            range "1..100";
          }
        }
      }
      leaf profile-capped {
        tailf:info
          "Configure Profile Cap";
        type empty;
      }
      container rate {
        tailf:info
          "Specify rates (CIR and PIR)";
        tailf:cli-embed-no-on-delete;
        tailf:cli-compact-syntax;
        tailf:cli-sequence-commands;
        leaf pir {
          tailf:cli-drop-node-name;
          tailf:cli-no-value-on-delete;
          type union {
            type uint32 {
              range "1..20000000";
            }
            type enumeration {
              enum "max";
            }
          }
        }
        leaf cir {
          tailf:cli-no-name-on-delete;
          tailf:cli-no-value-on-delete;
          type union {
            type uint32 {
              range "1..20000000";
            }
            type enumeration {
              enum "max";
            }
          }
        }
      }
      leaf stat-mode {
        tailf:info
          "Specify Stat Mode for the policer";
        tailf:cli-no-value-on-delete;
        type enumeration {
          enum "no-stats";
          enum "minimal";
          enum "offered-profile-no-cir";
          enum "offered-profile-cir";
          enum "offered-total-cir";
          enum "offered-limited-capped-cir";
          enum "offered-profile-capped-cir";
        }
      }
    }
    list queue {
      tailf:info
        "Configure a queue";
      tailf:cli-embed-no-on-delete;
      key "queue-id";
      leaf queue-id {
        type uint8 {
          range "1..8";
        }
      }
      container adaptation-rule {
        tailf:info
          "Specify the CIR and PIR adaptation rules";
        tailf:cli-embed-no-on-delete;
        tailf:cli-compact-syntax;
        leaf pir {
          tailf:info
            "<pir adaption-rule>";
          tailf:cli-no-name-on-delete;
          tailf:cli-no-value-on-delete;
          type enumeration {
            enum "max";
            enum "min";
            enum "closest";
          }
        }
        leaf cir {
          tailf:info
            "<cir adaption-rule>";
          tailf:cli-no-name-on-delete;
          tailf:cli-no-value-on-delete;
          type enumeration {
            enum "max";
            enum "min";
            enum "closest";
          }
        }
      }
      leaf adv-config-policy {
        tailf:info
          "Configure advanced configuration policy";
        tailf:cli-no-value-on-delete;
        type string {
          length "1..32";
        }
      }
      leaf burst-limit {
        tailf:info
          "Specify Burst limit";
        tailf:cli-no-value-on-delete;
        type union {
          type uint32 {
            range "1..14000000";
          }
          type enumeration {
            enum "default";
          }
        }
      }
      leaf cbs {
        tailf:info
          "Specify CBS rate";
        tailf:cli-no-value-on-delete;
        type union {
          type uint32 {
            range "0..131072";
          }
          type enumeration {
            enum "default";
          }
        }
      }
      leaf high-prio-only {
        tailf:info
          "Specify high priority only burst size";
        tailf:cli-no-value-on-delete;
        type union {
          type uint8 {
            range "0..100";
          }
        }
      }
      leaf mbs {
        tailf:info
          "Specify MBS rate";
        tailf:cli-no-value-on-delete;
        type union {
          type uint32 {
            range "0..134217728";
          }
          type enumeration {
            enum "default";
          }
        }
      }
      container parent {
        tailf:info
          "Specify the scheduler to which this queue feeds";
        tailf:cli-embed-no-on-delete;
        tailf:cli-compact-syntax;
        tailf:cli-sequence-commands;
        leaf name {
          tailf:cli-drop-node-name;
          tailf:cli-no-value-on-delete;
          type string {
            length "1..32";
          }
        }
        leaf weight {
          tailf:cli-no-name-on-delete;
          tailf:cli-no-value-on-delete;
          type uint8 {
            range "0..100";
          }
        }
        leaf level {
          tailf:cli-no-name-on-delete;
          tailf:cli-no-value-on-delete;
          type uint8 {
            range "1..8";
          }
        }
        leaf cir-weight {
          tailf:cli-no-name-on-delete;
          tailf:cli-no-value-on-delete;
          type uint8 {
            range "0..100";
          }
        }
        leaf cir-level {
          tailf:cli-no-name-on-delete;
          tailf:cli-no-value-on-delete;
          type uint8 {
            range "0..8";
          }
        }
      }
      container percent-rate {
        tailf:info
          "Specify Percent rates (CIR and PIR)";
        tailf:cli-embed-no-on-delete;
        tailf:cli-compact-syntax;
        tailf:cli-sequence-commands;
        leaf pir-percent {
          tailf:cli-drop-node-name;
          tailf:cli-no-value-on-delete;
          type decimal64 {
            fraction-digits 2;
            range "0.01..100.00";
          }
        }
        leaf cir {
          tailf:cli-no-name-on-delete;
          tailf:cli-no-value-on-delete;
          type decimal64 {
            fraction-digits 2;
            range "0.00..100.00";
          }
        }
      }
      leaf pool {
        tailf:info
          "Configure named pool for this queue";
        tailf:cli-no-value-on-delete;
        type string;
      }
      container port-parent {
        tailf:info
          "Specify the port-scheduler to which this queue feeds";
        tailf:cli-embed-no-on-delete;
        tailf:cli-compact-syntax;
        tailf:cli-sequence-commands;
        leaf weight {
          tailf:cli-no-name-on-delete;
          tailf:cli-no-value-on-delete;
          type uint8 {
            range "0..100";
          }
        }
        leaf level {
          tailf:cli-no-name-on-delete;
          tailf:cli-no-value-on-delete;
          type uint8 {
            range "1..8";
          }
        }
        leaf cir-weight {
          tailf:cli-no-name-on-delete;
          tailf:cli-no-value-on-delete;
          type uint8 {
            range "0..100";
          }
        }
        leaf cir-level {
          tailf:cli-no-name-on-delete;
          tailf:cli-no-value-on-delete;
          type uint8 {
            range "0..8";
          }
        }
      }
      container rate {
        tailf:info
          "Specify rates (CIR and PIR)";
        tailf:cli-embed-no-on-delete;
        tailf:cli-compact-syntax;
        tailf:cli-sequence-commands;
        leaf pir {
          tailf:cli-drop-node-name;
          tailf:cli-no-value-on-delete;
          type union {
            type uint32 {
              range "1..10000000";
            }
            type enumeration {
              enum "max";
            }
          }
        }
        leaf cir {
          tailf:cli-no-name-on-delete;
          tailf:cli-no-value-on-delete;
          type union {
            type uint32 {
              range "0..10000000";
            }
            type enumeration {
              enum "max";
            }
          }
        }
      }
    }
  }

  grouping dhcp-lease-time {
    leaf days {
      tailf:cli-no-name-on-delete;
      tailf:cli-no-value-on-delete;
      type uint16 {
        range "0..3650";
      }
    }
    leaf hrs {
      tailf:cli-no-name-on-delete;
      tailf:cli-no-value-on-delete;
      type uint16 {
        range "0..23";
      }
    }
    leaf min {
      tailf:cli-no-name-on-delete;
      tailf:cli-no-value-on-delete;
      type uint16 {
        range "0..59";
      }
    }
    leaf sec {
      tailf:cli-no-name-on-delete;
      tailf:cli-no-value-on-delete;
      type uint16 {
        range "0..59";
      }
    }
  }

  augment "/ncs:devices/ncs:device/ncs:config" {
    list card {
      tailf:ncs-device-type "cli-ned";
      tailf:display-when "not(../ncs:module) or ../ncs:module[ncs:name='tailf-ned-alu-sr']";
      tailf:info
        "Configure an I/O module in a specified slot";
      tailf:cli-recursive-delete;
      tailf:cli-embed-no-on-delete;
      key "slot-number";
      leaf slot-number {
        type string;
      }
      leaf card-type {
        tailf:info
          "Add/remove an I/O module to/from the device";
        tailf:cli-no-value-on-delete;
        type string;
      }
      leaf fail-on-error {
        tailf:info
          "Configure the behavior of card-state upon errors detected";
        type empty;
      }
      list mda {
        tailf:info
          "Configure a media dependant adapter";
        tailf:cli-embed-no-on-delete;
        key "mda-slot";
        leaf mda-slot {
          type string;
        }
        leaf mda-type {
          tailf:info
            "Provisions/de-provisions an MDA to/from the device";
          tailf:cli-no-value-on-delete;
          type string;
        }
        container access {
          tailf:info
            "Configure access MDA parameters";
          tailf:cli-add-mode;
          container ingress {
            tailf:info
              "Configure access ingress MDA parameters";
            tailf:cli-add-mode;
            leaf fabric-policy {
              tailf:info
                "Configure the network policy";
              tailf:cli-no-value-on-delete;
              tailf:non-strict-leafref {
                path "/ncs:devices/ncs:device/ncs:config/alu:qos/fabric-profile/policy-id" {
                  tailf:xpath-root 3;
                }
              }
              type uint16;
            }
          }
        }
        container network {
          tailf:info
            "Configure network MDA parameters";
          tailf:cli-add-mode;
          container ingress {
            tailf:info
              "Configure network ingress MDA parameters";
            tailf:cli-add-mode;
            leaf fabric-policy {
              tailf:info
                "Configure the network policy";
              tailf:cli-no-value-on-delete;
              tailf:non-strict-leafref {
                path "/ncs:devices/ncs:device/ncs:config/alu:qos/fabric-profile/policy-id" {
                  tailf:xpath-root 3;
                }
              }
              type uint16;
            }
            container pool {
              tailf:info
                "Configure the ingress pool policy for the MDA";
              tailf:cli-add-mode;
              leaf slope-policy {
                tailf:info
                  "Configure the slope policy";
                tailf:cli-no-value-on-delete;
                type string {
                  length "1..32";
                }
              }
            }
            leaf queue-policy {
              tailf:info
                "Configure the network policy";
              type string;
            }
          }
        }
        leaf shutdown {
          tailf:cli-boolean-no;
          default "false";
          type boolean;
        }
      }
      list fp {
        key "id";
        leaf id {
          type uint32;
        }
        container ingress {
          tailf:cli-add-mode;
          container mcast-path-management {
            tailf:cli-add-mode;
            leaf bandwidth-policy {
              type string;
            }
            leaf shutdown {
              tailf:cli-boolean-no;
              default "true";
              type boolean;
            }
          }
        }
      }
      leaf shutdown {
        tailf:cli-boolean-no;
        default "false";
        type boolean;
      }
    }
    container cflowd {
      tailf:ncs-device-type "cli-ned";
      tailf:display-when "not(../../ncs:module) or ../../ncs:module[ncs:name='tailf-ned-alu-sr']";
      presence "present";
      tailf:info
        "Configure CFlowd";
      tailf:cli-add-mode;
      leaf active-timeout {
        tailf:cli-no-value-on-delete;
        tailf:info
          "Cflowd active timeout";
        type uint16 {
          range "1..600";
        }
      }
      leaf cache-size {
        tailf:cli-no-value-on-delete;
        tailf:info
          "Configure maximum number of flows in the Cflowd cache table";
        type uint32;
      }
      list collector {
        tailf:info
          "Configure a Cflowd data collector";
        key "collector-id";
        leaf collector-id {
          tailf:cli-drop-node-name;
          type union {
            type inet:ipv4-address;
            type inet:ipv6-address;
          }
        }
        leaf version {
          tailf:cli-hide-in-submode;
          tailf:cli-no-name-on-delete;
          tailf:cli-no-value-on-delete;
          type enumeration {
            enum "5";
            enum "8";
            enum "9";
            enum "10";
          }
        }
        leaf description {
          tailf:info
            "Configure description for this Cflowd collector";
          tailf:cli-no-value-on-delete;
          type string {
            length "1..80";
          }
        }
        leaf template-set {
          tailf:info
            "Configure the template set for this Cflowd collector";
          tailf:cli-no-name-on-delete;
          tailf:cli-no-value-on-delete;
          when "../version='9' or ../version='10'" {
            tailf:xpath-root 3;
            tailf:dependency "../version";
          }
          type enumeration {
            enum "basic";
            enum "mpls-ip";
          }
        }
        leaf autonomous-system-type {
          tailf:info
            "Configures AS information based on origination or external peer AS routes";
          tailf:cli-no-name-on-delete;
          tailf:cli-no-value-on-delete;
          when "../version='5'" {
            tailf:xpath-root 3;
          }
          type enumeration {
            enum "origin";
            enum "peer";
          }
        }
        leaf shutdown {
          tailf:info
            "Configure description for this Cflowd collector";
          type empty;
        }
      }
      leaf export-mode {
        tailf:info
          "Configure Cflowd Export Mode";
        tailf:cli-no-value-on-delete;
        tailf:cli-no-name-on-delete;
        type enumeration {
          enum "automatic";
          enum "manual";
        }
        default "automatic";
      }
      leaf inactive-timeout {
        tailf:info
          "Configure Cflowd inactive timeout";
        tailf:cli-no-value-on-delete;
        type uint16 {
          range "10..600";
        }
      }
      leaf overflow {
        tailf:info
          "Configure percentage of entries to be removed from Cflowd cache when the maximum number of entries has been exceeded";
        tailf:cli-no-value-on-delete;
        type uint8 {
          range "1..50";
        }
      }
      leaf rate {
        tailf:info
          "Configure the rate at which traffic is sampled and sent for Cflowd analysis";
        tailf:cli-no-value-on-delete;
        type uint16 {
          range "1..10000";
        }
      }
      leaf template-retransmit {
        tailf:info
          "Configure the time interval to resend template information";
        tailf:cli-no-value-on-delete;
        type uint16 {
          range "1..600";
        }
      }
      leaf shutdown {
        tailf:info
          "Administratively enable/disable Cflowd sampling";
        type empty;
      }
    }
    container ipsec {
      tailf:ncs-device-type "cli-ned";
      tailf:display-when "not(../../ncs:module) or ../../ncs:module[ncs:name='tailf-ned-alu-sr']";
      tailf:info
        "Configure IPsec Parameters";
      tailf:cli-add-mode;
      list ike-policy {
        tailf:info
          "Configure IPsec IKE Policy";
        tailf:cli-embed-no-on-delete;
        key "ike-policy-id";
        leaf ike-policy-id {
          type uint16 {
            range "1..2048";
          }
        }
        leaf auth-algorithm {
          tailf:info
            "Configure Authentication Algorithm for this IKE policy";
          tailf:cli-no-value-on-delete;
          type enumeration {
            enum "md5";
            enum "sha1";
            enum "sha256";
            enum "sha384";
            enum "sha512";
            enum "aes-xcbc";
          }
        }
        leaf auth-method {
          tailf:info
            "Configure authentication method for this IKE policy";
          tailf:cli-no-value-on-delete;
          type enumeration {
            enum "psk";
            enum "plain-psk-xauth";
            enum "cert-auth";
            enum "psk-radius";
            enum "cert-radius";
            enum "eap";
            enum "auto-eap-radius";
            enum "auto-eap";
          }
        }
        leaf auto-eap-method {
          tailf:info
            "Configure auto EAP method";
          tailf:cli-no-name-on-delete;
          tailf:cli-no-value-on-delete;
          type enumeration {
            enum "psk";
            enum "cert";
            enum "psk-or-cert";
          }
        }
        leaf auto-eap-own-method {
          tailf:info
            "Configure auto EAP method for itself";
          tailf:cli-no-name-on-delete;
          tailf:cli-no-value-on-delete;
          type enumeration {
            enum "psk";
            enum "cert";
          }
        }
        leaf description {
          tailf:info
            "Configure description for this IKE policy";
          tailf:cli-no-value-on-delete;
          type string {
            length "1..80";
          }
        }
        leaf dh-group {
          tailf:info
            "Configure dh-group for this IKE policy";
          tailf:cli-no-value-on-delete;
          type enumeration {
            enum "1";
            enum "2";
            enum "5";
            enum "14";
            enum "15";
          }
        }
        container dpd {
          presence "present";
          tailf:info
            "Configure DPD Parameters";
          tailf:cli-compact-syntax;
          leaf interval {
            tailf:cli-no-name-on-delete;
            tailf:cli-no-value-on-delete;
            type uint16 {
              range "10..300";
            }
          }
          leaf max-retries {
            tailf:cli-no-name-on-delete;
            tailf:cli-no-value-on-delete;
            type uint8 {
              range "2..5";
            }
          }
          leaf reply-only {
            tailf:cli-no-name-on-delete;
            tailf:cli-no-value-on-delete;
            type empty;
          }
        }
        leaf encryption-algorithm {
          tailf:info
            "Configure Encryption Algorithm for this IKE policy";
          tailf:cli-no-value-on-delete;
          type enumeration {
            enum "des";
            enum "3des";
            enum "aes128";
            enum "aes192";
            enum "aes256";
          }
        }
        leaf ike-mode {
          tailf:info
            "Configure IKE mode for this IKE policy";
          tailf:cli-no-value-on-delete;
          type enumeration {
            enum "main";
            enum "aggressive";
          }
        }
        leaf ike-version {
          tailf:info
            "Configure version of IKE";
          tailf:cli-no-name-on-delete;
          tailf:cli-no-value-on-delete;
          type uint8 {
            range "1..2";
          }
        }
        leaf ipsec-lifetime {
          tailf:info
            "Configure Phase2 life time for this IKE policy";
          tailf:cli-no-value-on-delete;
          type uint32 {
            range "1200..172800";
          }
        }
        leaf isakmp-lifetime {
          tailf:info
            "Configure Phase2 life time for this IKE policy";
          tailf:cli-no-value-on-delete;
          type uint32 {
            range "1200..172800";
          }
        }
        leaf match-peer-id-to-cert {
          tailf:info
            "Enable/disable matching of peer identifier with certificate";
          type empty;
        }
        container nat-traversal {
          presence "present";
          tailf:info
            "Configure NAT Traversal Parameters";
          tailf:cli-compact-syntax;
          leaf force {
            tailf:cli-no-name-on-delete;
            type empty;
          }
          leaf keep-alive-interval {
            tailf:cli-no-name-on-delete;
            tailf:cli-no-value-on-delete;
            type uint16 {
              range "120..600";
            }
          }
          leaf force-keep-alive {
            tailf:cli-no-name-on-delete;
            type empty;
          }
        }
        leaf own-auth-method {
          tailf:info
            "Configure authentication method for IKE policy itself";
          tailf:cli-no-value-on-delete;
          type enumeration {
            enum "psk";
            enum "cert";
            enum "eap-only";
          }
        }
        container pfs {
          presence "present";
          tailf:info
            "Configure PFS for this IKE policy";
          tailf:cli-compact-syntax;
          leaf dh-group {
            tailf:cli-no-value-on-delete;
            tailf:cli-no-name-on-delete;
            type enumeration {
              enum "1";
              enum "2";
              enum "5";
              enum "14";
              enum "15";
            }
          }
        }
      }
      list ipsec-transform {
        tailf:info
          "Configure IPsec Transform";
        tailf:cli-embed-no-on-delete;
        key "transform-id";
        leaf transform-id {
          type uint16 {
            range "1..2048";
          }
        }
        leaf esp-auth-algorithm {
          tailf:info
            "Configure Authentication Algorithm for this transform";
          tailf:cli-no-value-on-delete;
          type enumeration {
            enum "null";
            enum "md5";
            enum "sha1";
            enum "sha256";
            enum "sha384";
            enum "sha512";
            enum "aes-xcbc";
          }
        }
        leaf esp-encryption-algorithm {
          tailf:info
            "Configure Encryption Algorithm for this transform";
          tailf:cli-no-value-on-delete;
          type enumeration {
            enum "null";
            enum "des";
            enum "3des";
            enum "aes128";
            enum "aes192";
            enum "aes256";
          }
        }
      }
    }
    container isa {
      tailf:ncs-device-type "cli-ned";
      tailf:display-when "not(../../ncs:module) or ../../ncs:module[ncs:name='tailf-ned-alu-sr']";
      tailf:info
        "Configure Integrated Services Adaptors";
      tailf:cli-recursive-delete;
      tailf:cli-embed-no-on-delete;
      list tunnel-group {
        tailf:info
          "Configure an ISA Tunnel Group";
        key "tunnel-group-id";
        leaf tunnel-group-id {
          tailf:cli-drop-node-name;
          type uint16 {
            range "1..16";
          }
        }
        leaf primary {
          tailf:info
            "Configure ISA-Tunnel-Group primary ISA";
          type string;
        }
        leaf shutdown {
          tailf:info
            "Administratively enable/disable an ISA-Tunnel-Group";
          tailf:cli-boolean-no;
          default "true";
          type boolean;
        }
      }
    }
    list lag {
      tailf:ncs-device-type "cli-ned";
      tailf:display-when "not(../ncs:module) or ../ncs:module[ncs:name='tailf-ned-alu-sr']";
      tailf:info
        "Create/delete context for configuring LAG attributes";
      tailf:cli-embed-no-on-delete;
      tailf:cli-recursive-delete;
      tailf:cli-diff-dependency "/alu:port" {
        tailf:xpath-root 3;
      }
      key "id";
      leaf id {
        type uint32;
      }
      leaf description {
        tailf:cli-no-value-on-delete;
        type string;
      }
      leaf mode {
        tailf:info
          "<mode>;;access|network|hybrid";
        tailf:cli-no-value-on-delete;
        type enumeration {
          enum "access";
          enum "network";
          enum "hybrid";
        }
      }
      leaf encap-type {
        tailf:info
          "Encapsulation type";
        tailf:cli-no-value-on-delete;
        type enumeration {
          enum "dot1q";
          enum "null";
          enum "qinq";
        }
      }
      list port {
        tailf:cli-suppress-mode;
        key "id";
        leaf id {
          tailf:non-strict-leafref {
            path "/ncs:devices/ncs:device/ncs:config/alu:port/port-id" {
              tailf:xpath-root 3;
            }
          }
          type string;
        }
        leaf priority {
          type uint32;
        }
      }
      container port-threshold {
        tailf:cli-embed-no-on-delete;
        tailf:cli-compact-syntax;
        tailf:cli-sequence-commands;
        leaf value {
          tailf:cli-drop-node-name;
          tailf:cli-no-value-on-delete;
          type uint8 {
            range "0..31";
          }
        }
        leaf action {
          type enumeration {
            enum "dynamic-cost";
            enum "down";
          }
        }
      }
      container lacp {
        tailf:cli-embed-no-on-delete;
        tailf:cli-compact-syntax;
        tailf:cli-sequence-commands;
        leaf mode {
          tailf:cli-drop-node-name;
          tailf:cli-no-value-on-delete;
          type enumeration {
            enum "passive";
            enum "active";
          }
        }
        leaf administrative-key {
          tailf:cli-no-value-on-delete;
          tailf:cli-no-name-on-delete;
          tailf:cli-optional-in-sequence;
          type uint16;
        }
        leaf system-id {
          tailf:cli-no-value-on-delete;
          tailf:cli-no-name-on-delete;
          tailf:cli-optional-in-sequence;
          type string;
        }
        leaf system-priority {
          tailf:cli-no-value-on-delete;
          tailf:cli-no-name-on-delete;
          type uint16;
        }
      }
      leaf shutdown {
        tailf:cli-boolean-no;
        default "true";
        type boolean;
      }
    }
    list port {
      tailf:ncs-device-type "cli-ned";
      tailf:display-when "not(../ncs:module) or ../ncs:module[ncs:name='tailf-ned-alu-sr']";
      tailf:info
        "Configure physical ports";
      tailf:cli-recursive-delete;
      tailf:cli-embed-no-on-delete;
      key "port-id";
      leaf port-id {
        type string;
      }
      leaf description {
        tailf:cli-no-value-on-delete;
        type string;
      }
      container ethernet {
        tailf:info
          "Configure attributes for an ethernet port";
        tailf:cli-add-mode;
        leaf mode {
          tailf:info
            "Configure an ethernet port for access or network mode";
          tailf:cli-no-value-on-delete;
          tailf:cli-diff-dependency "../network" {
            tailf:xpath-root 3;
            tailf:cli-trigger-on-all;
          }
          tailf:cli-diff-dependency "../access" {
            tailf:xpath-root 3;
            tailf:cli-trigger-on-all;
          }
          type enumeration {
            enum "access";
            enum "network";
            enum "hybrid";
          }
        }
        container access {
          tailf:info
            "Configure ethernet access port parameters";
          tailf:cli-add-mode;
          tailf:cli-diff-dependency "../mode" {
            tailf:xpath-root 3;
          }
          leaf accounting-policy {
            tailf:info
              "Configure the accounting policy which applies to the access port";
            tailf:cli-embed-no-on-delete;
            tailf:cli-no-value-on-delete;
            type uint8 {
              range "0..99";
            }
          }
          leaf collect-stats {
            tailf:info
              "Enable/disable the collection of statistical data";
            tailf:cli-embed-no-on-delete;
            type empty;
          }
          container egress {
            tailf:info
              "Configure ethernet access egress port parameters";
            tailf:cli-add-mode;
            leaf qos {
              tailf:cli-embed-no-on-delete;
              type uint16 {
                range "1..65535";
              }
            }
          }
        }
        container autonegotiate {
          tailf:info
            "Enable/disable speed and duplex autonegotiation on an ethernet port";
          tailf:cli-embed-no-on-delete;
          presence "true";
          leaf limited {
            tailf:cli-no-name-on-delete;
            type empty;
          }
        }
        leaf dot1q-etype {
          tailf:info
            "Configure the ethertype used for dot1q encapsulation";
          tailf:cli-no-value-on-delete;
          type uint32 {
            range "1536..65535";
          }
        }
        leaf duplex {
          tailf:info
            "Configure duplex of an ethernet port";
          tailf:cli-no-value-on-delete;
          type enumeration {
            enum "full";
            enum "half";
          }
        }
        container efm-oam {
          tailf:info
            "Configure EFM-OAM attributes";
          tailf:cli-add-mode;
          leaf accept-remote-loopback {
            type empty;
          }
          container transmit-interval {
            tailf:cli-compact-syntax;
            tailf:cli-sequence-commands;
            leaf interval {
              tailf:cli-drop-node-name;
              type uint16 {
                range "1..600";
              }
            }
            leaf multiplier {
              type uint8 {
                range "2..5";
              }
            }
          }
        }
        leaf encap-type {
          tailf:info
            "Configure encapsulation method";
          tailf:cli-no-value-on-delete;
          type enumeration {
            enum "dot1q";
            enum "null";
            enum "qinq";
          }
        }
        leaf egress-rate {
          tailf:info
            "Specify the egress-rate";
          tailf:cli-no-value-on-delete;
          type uint32 {
            range "1..10000000";
          }
        }
        leaf egress-scheduler-policy {
          tailf:info
            "Configure an egress scheduler policy";
          tailf:cli-no-value-on-delete;
          tailf:cli-embed-no-on-delete;
          tailf:cli-diff-dependency "/alu:qos/port-scheduler-policy" {
            tailf:xpath-root 3;
          }
          tailf:non-strict-leafref {
            path "/ncs:devices/ncs:device/ncs:config/alu:qos/port-scheduler-policy/name" {
              tailf:xpath-root 3;
            }
          }
          type string;
        }
        container egress-scheduler-override {
          tailf:info
            "Apply egress scheduler overrides";
          tailf:cli-embed-no-on-delete;
          tailf:cli-diff-dependency "../egress-scheduler-policy" {
            tailf:xpath-root 3;
          }
          tailf:cli-add-mode;
          list level {
            tailf:info
              "Configure priority level parameters";
            tailf:cli-suppress-mode;
            tailf:cli-compact-syntax;
            tailf:cli-sequence-commands;
            key "priority-level";
            leaf priority-level {
              type uint8 {
                range "1..8";
              }
            }
            leaf rate {
              tailf:cli-no-value-on-delete;
              tailf:cli-no-name-on-delete;
              type union {
                type uint32 {
                  range "1..40000000";
                }
                type enumeration {
                  enum "max";
                }
              }
            }
            leaf cir {
              tailf:cli-no-value-on-delete;
              tailf:cli-no-name-on-delete;
              type union {
                type uint32 {
                  range "0..40000000";
                }
                type enumeration {
                  enum "max";
                }
              }
            }
          }
          leaf max-rate {
            tailf:cli-no-value-on-delete;
            type union {
              type uint32 {
                range "1..40000000";
              }
              type enumeration {
                enum "max";
              }
            }
          }
        }
        container hold-time {
          tailf:info
            "Configure port link dampening timers";
          tailf:cli-embed-no-on-delete;
          tailf:cli-compact-syntax;
          tailf:cli-sequence-commands;
          leaf up {
            tailf:cli-no-name-on-delete;
            tailf:cli-no-value-on-delete;
            type uint32 {
              range "0..90000";
            }
          }
          leaf down {
            tailf:cli-no-name-on-delete;
            tailf:cli-no-value-on-delete;
            type uint32 {
              range "0..90000";
            }
          }
          leaf unit {
            tailf:cli-drop-node-name;
            tailf:cli-no-value-on-delete;
            type enumeration {
              enum "seconds";
              enum "centiseconds";
            }
          }
        }
        leaf ingress-rate {
          tailf:info
            "Configure the maximum amount of ingress bandwidth that this port can receive";
          tailf:cli-no-value-on-delete;
          type uint32 {
            range "1..100000";
          }
        }
        container lldp {
          tailf:info
            "Configure Link Layer Discovery Protocol parameters";
          tailf:cli-add-mode;
          list dest-mac {
            tailf:info
              "Configure the destination mac-address parameters";
            max-elements 3;
            key "id";
            leaf id {
              type enumeration {
                enum "nearest-bridge";
                enum "nearest-non-tpmr";
                enum "nearest-customer";
              }
            }
            leaf notification {
              tailf:info
                "Enable/Disable LLDP notifications";
              tailf:cli-embed-no-on-delete;
              type empty;
            }
            leaf admin-status {
              tailf:info
                "Configure LLDP transmission/reception frame handling";
              type enumeration {
                enum "rx";
                enum "tx";
                enum "tx-rx";
                enum "disabled";
              }
            }
            container tx-tlvs {
              tailf:info
                "Configure the LLDP TLVs to transmit";
              tailf:cli-compact-syntax;
              leaf port-desc {
                type empty;
              }
              leaf sys-name {
                type empty;
              }
              leaf sys-desc {
                type empty;
              }
              leaf sys-cap {
                type empty;
              }
            }
            leaf tx-mgmt-address {
              tailf:info
                "Configure which management address to transmit";
              type enumeration {
                enum "system";
              }
            }
          }
        }
        leaf mac {
          tailf:info
            "Assign a specific MAC address to an ethernet port";
          tailf:cli-no-value-on-delete;
          type ieee-mac;
        }
        leaf mtu {
          tailf:info
            "Configure the maximum payload MTU for an ethernet port";
          tailf:cli-no-value-on-delete;
          type uint16;
        }
        container network {
          tailf:info
            "Configure network port parameters";
          tailf:cli-diff-dependency "../mode" {
            tailf:xpath-root 3;
            tailf:cli-trigger-on-set;
          }
          tailf:cli-recursive-delete;
          tailf:cli-add-mode;
          leaf queue-policy {
            tailf:info
              "Configure the network policy";
            tailf:cli-no-value-on-delete;
            tailf:non-strict-leafref {
              path "/ncs:devices/ncs:device/ncs:config/alu:qos/network-queue/network-queue-name" {
                tailf:xpath-root 3;
              }
            }
            type string;
          }
          leaf scheduler-mode {
            tailf:info
              "Configure egress scheduler mode";
            tailf:cli-no-value-on-delete;
            tailf:cli-no-name-on-delete;
            type enumeration {
              enum "profile";
              enum "4-priority";
              enum "16-priority";
            }
          }
        }
      }
      container dwdm {
        tailf:info
          "Configure the Dense Wavelength Division Multiplexing parameters";
        tailf:cli-add-mode;
        container amplifier {
          tailf:info
            "Configure the optical port amplifier parameters";
          tailf:cli-add-mode;
          leaf-list report-alarms {
            tailf:info
              "Enable/disable logging of optical amplifier alarms on port";
            type enumeration {
              enum "ild";
              enum "tmp";
              enum "mth";
              enum "mtl";
              enum "los";
              enum "lop";
              enum "com";
            }
          }
        }
        leaf channel {
          tailf:info
            "Configure the DWDM channel number";
          type uint16 {
            range "0 | 17..61| 175..605";
            tailf:info
              "<dwdm channel>;;[0|17-61|175-605]";
          }
        }
        container coherent {
          tailf:cli-add-mode;
          leaf target-power {
            type decimal64 {
              range "-20..3";
              fraction-digits 3;
              tailf:info
                "<dwdm target power in dBM>[-20.00..3.00]";
            }
          }
          leaf compatibility {
            type enumeration {
              enum "interop";
              enum "interop2";
            }
          }
          container sweep {
            tailf:cli-compact-syntax;
            leaf start {
              type int32;
            }
            leaf end {
              type int32;
            }
          }
          leaf channel {
            type uint16 {
              range "0 | 17..61| 175..605";
              tailf:info
                "<dwdm channel>;;[0|17-61|175-605]";
            }
          }
          leaf mode {
            type enumeration {
              enum "manual";
            }
          }
        }
        leaf rxdtv-adjust {
          tailf:info
            "Enable/Disable Rx Decision Threshold Voltage Adjustment feedback.";
          type empty;
        }
        container tdcm {
          tailf:info
            "Configure the Tunable Dispersion Compensation Module parameters";
          tailf:cli-add-mode;
          leaf channel {
            tailf:info
              "Configure the tdcm received channel number";
            type uint16 {
              range "0 | 17..61| 175..605";
            }
          }
          leaf dispersion {
            tailf:info
              "Configure the dispersion compensation (ps/nm)";
            type int32 {
              range "-1200..1200";
            }
          }
          leaf mode {
            tailf:info
              "Configure the dispersion algorithm mode used";
            type enumeration {
              enum "automatic";
              enum "manual";
            }
          }
          leaf-list report-alarms {
            tailf:info
              "Enable/disable logging of tdcm alarms on port";
            type enumeration {
              enum "ild";
              enum "tmp";
              enum "mth";
              enum "mtl";
              enum "los";
              enum "lop";
              enum "com";
            }
          }
          container sweep {
            tailf:info
              "Configure the dispersion sweep start and end values for the link (ps/nm)";
            tailf:cli-compact-syntax;
            tailf:cli-sequence-commands;
            leaf start {
              type int32 {
                range "-1200..1200";
              }
            }
            leaf end {
              type int32 {
                range "-1200..1200";
              }
            }
          }
          leaf shutdown {
            tailf:info
              "Administratively enable/disable the channel";
            tailf:cli-boolean-no;
            default "true";
            type boolean;
          }
        }
      }
      container modify-buffer-allocation-rate {
        tailf:info
          "Configure modify buffer allocation rate";
        tailf:cli-add-mode;
        leaf egr-percentage-of-rate {
          tailf:cli-no-value-on-delete;
          tailf:info
            "Configure egress percentage of rate";
          type uint16 {
            range "1..1000";
          }
        }
        leaf ing-percentage-of-rate {
          tailf:cli-no-value-on-delete;
          tailf:info
            "Configure ingress percentage of rate";
          type uint16 {
            range "1..1000";
          }
        }
      }
      container multilink-bundle {
        tailf:cli-add-mode;
        leaf fragment-threshold {
          tailf:info
            "Configure the maximum bytes of a fragment transmitted";
          tailf:cli-no-value-on-delete;
          type union {
            type uint16 {
              range "128..512";
            }
            type enumeration {
              enum "unlimited";
            }
          }
        }
        list member {
          tailf:info
            "Add a member port to the bundle";
          tailf:cli-embed-no-on-delete;
          tailf:cli-suppress-mode;
          key "id";
          leaf id {
            type string;
          }
        }
      }
      container network {
        tailf:info
          "Configure the network parameters for a port";
        tailf:cli-recursive-delete;
        tailf:cli-add-mode;
        container egress {
          tailf:info
            "Configure network egress port parameters";
          tailf:cli-add-mode;
          container pool {
            tailf:info
              "Configure the egress pool policy for the port";
            tailf:cli-add-mode;
            leaf slope-policy {
              tailf:info
                "Configure the slope policy";
              tailf:cli-no-value-on-delete;
              type string {
                length "1..32";
              }
            }
          }
        }
      }
      container otu {
        tailf:info
          "Configure Optical Transport Unit (OTU) parameters";
        tailf:cli-embed-no-on-delete;
        tailf:cli-add-mode;
        leaf async-mapping {
          tailf:info
            "Enable/Disable OTU asynchronous mapping; synchronous when disabled";
          type empty;
        }
        leaf fec {
          tailf:info
            "Configure the Forwarding Error Correction (FEC) params";
          tailf:cli-no-value-on-delete;
          type enumeration {
            enum "g709";
            enum "enhanced";
          }
        }
        leaf otu2-lan-data-rate {
          tailf:info
            "Configure the 10GE LAN OTU2 Data Rate";
          type enumeration {
            enum "11.049";
            enum "11.096";
          }
        }
        leaf-list report-alarms {
          tailf:info
            "Enable/Disable the OTU alarms";
          type enumeration {
            enum "loc";
            enum "los";
            enum "lof";
            enum "lom";
            enum "otu-ais";
            enum "otu-ber-sf";
            enum "otu-ber-sd";
            enum "otu-bdi";
            enum "otu-tim";
            enum "otu-iae";
            enum "otu-biae";
            enum "fec-sf";
            enum "fec-sd";
            enum "fec-fail";
            enum "fec-uncorr";
            enum "odu-ais";
            enum "odu-oci";
            enum "odu-lck";
            enum "odu-bdi";
            enum "odu-tim";
            enum "opu-tim";
            enum "opu-plm";
          }
        }
        leaf sd-threshold {
          tailf:info
            "Configure the Signal Degrade (SD) threshold";
          type uint8 {
            range "5..9";
          }
        }
        leaf sf-sd-method {
          tailf:info
            "Configure the Signal Fail/Degrade method for the port";
          type enumeration {
            enum "bip8";
            enum "fec";
          }
        }
        leaf sf-threshold {
          tailf:info
            "Configure the Signal Fail (SF) threshold";
          type uint8 {
            range "3..6";
          }
        }
      }
      container sonet-sdh {
        tailf:cli-add-mode;
        leaf clock-source {
          tailf:info
            "Configure the clock for transmitted data";
          tailf:cli-no-value-on-delete;
          type enumeration {
            enum "loop-timed";
            enum "node-timed";
          }
        }
        leaf framing {
          tailf:info
            "Configure SONET/SDH framing";
          tailf:cli-no-value-on-delete;
          type enumeration {
            enum "sonet";
            enum "sdh";
          }
        }
        container group {
          tailf:info
            "Configure the payload of the SONET/SDH group";
          tailf:cli-embed-no-on-delete;
          tailf:cli-compact-syntax;
          tailf:cli-sequence-commands;
          leaf sonet-sdh-index {
            tailf:cli-drop-node-name;
            tailf:cli-no-value-on-delete;
            type uint32;
          }
          leaf payload {
            tailf:cli-no-value-on-delete;
            type enumeration {
              enum "tu3";
              enum "vt2";
              enum "vt15";
            }
          }
        }
        container hold-time {
          tailf:info
            "Configure SONET link dampening timers in 100s of ms";
          tailf:cli-embed-no-on-delete;
          tailf:cli-compact-syntax;
          leaf up {
            tailf:cli-no-value-on-delete;
            tailf:cli-no-name-on-delete;
            type uint8 {
              range "0..100";
            }
          }
          leaf down {
            tailf:cli-no-value-on-delete;
            tailf:cli-no-name-on-delete;
            type uint8 {
              range "0..100";
            }
          }
        }
        leaf loopback {
          tailf:info
            "Activate a loopback on the SONET port";
          tailf:cli-no-value-on-delete;
          type enumeration {
            enum "line";
            enum "internal";
          }
        }
        list path {
          tailf:info
            "Configure SONET/SDH path properties";
          tailf:cli-embed-no-on-delete;
          key "sonet-sdh-index";
          leaf sonet-sdh-index {
            tailf:info
              "sts12/sts3/tu3/vt2/vt15/sts1 sonet-sdh index";
            type string;
          }
          leaf payload {
            tailf:info
              "Configure the SONET/SDH path payload";
            type enumeration {
              enum "sts3";
              enum "tug3";
              enum "ds3";
              enum "e3";
              enum "vt2";
              enum "vt15";
              enum "ds1";
              enum "e1";
            }
          }
        }
        leaf report-alarm {
          tailf:info
            "Enable/disable logging of line and section alarms for a port";
          type enumeration {
            enum "lais";
            enum "lrdi";
            enum "ss1f";
            enum "lb2er-sd";
            enum "lb2er-sf";
            enum "slof";
            enum "slos";
            enum "lrei";
            enum "loc";
          }
        }
        container section-trace {
          tailf:info
            "Configure section trace bytes in the SONET section header";
          choice a {
            leaf increment-z0 {
              type empty;
            }
            leaf byte {
              type uint8;
            }
            leaf string {
              type string {
                length "1..16";
              }
            }
          }
        }
        leaf single-fiber {
          tailf:info
            "Enable/disable single fiber";
          type empty;
        }
        leaf speed {
          tailf:info
            "Configure the speed of a port to be either OC3 or OC12";
          tailf:cli-no-value-on-delete;
          type enumeration {
            enum "oc3";
            enum "oc8";
          }
        }
        leaf suppress-lo-alarm {
          tailf:info
            "Suppress lo order alarms";
          type empty;
        }
        container threshold {
          tailf:info
            "Configure the line signal degradation BER thresholds";
          tailf:cli-compact-syntax;
          tailf:cli-sequence-commands;
          tailf:cli-embed-no-on-delete;
          leaf value {
            tailf:cli-drop-node-name;
            tailf:cli-no-value-on-delete;
            type enumeration {
              enum "ber-sd";
              enum "ber-sf";
            }
          }
          leaf rate {
            tailf:cli-no-value-on-delete;
            type uint8 {
              range "3..9";
            }
          }
        }
        leaf tx-dus {
          tailf:info
            "Enable/disable the forced transmit in S1 overhead byte";
          type empty;
        }
      }
      container tdm {
        tailf:info
          "Configure attributes for a TDM port";
        tailf:cli-add-mode;
        leaf buildout {
          tailf:info
            "Configure the line buildout for the physical DS1/DS3";
          type enumeration {
            enum "long";
            enum "short";
          }
        }
        list ds1 {
          tailf:info
            "Configure DS1 channel parameters";
          tailf:cli-embed-no-on-delete;
          key "ds1-id";
          leaf ds1-id {
            tailf:info
              "ds1-number(1-28)|ds1-sonet-sdh-index";
            type string;
          }
          container bert {
            tailf:info
              "Start/Stop a Bit Error Rate Test (BERT)";
            tailf:cli-embed-no-on-delete;
            tailf:cli-compact-syntax;
            tailf:cli-sequence-commands;
            leaf value {
              tailf:cli-no-value-on-delete;
              type enumeration {
                enum "2e3";
                enum "2e9";
                enum "2e11";
                enum "2e15";
                enum "2e20";
                enum "2e20q";
                enum "2e23";
                enum "ones";
                enum "zeros";
                enum "alternating";
              }
            }
            leaf duration {
              tailf:info
                "sec|hh:mm[:sec] 24 hour max";
              tailf:cli-no-value-on-delete;
              type string;
            }
          }
          leaf bit-error-insertion {
            tailf:info
              "Configure the bit error insert rate for the BERT test";
            tailf:cli-no-value-on-delete;
            type uint8 {
              range "2..7";
            }
          }
          list channel-group {
            tailf:info
              "Create/delete DS0 channel groups";
            tailf:cli-embed-no-on-delete;
            max-elements 24;
            key "id";
            leaf id {
              type uint8 {
                range "1..24";
              }
            }
            leaf clock-source {
              tailf:info
                "Configure the clock for transmitted data";
              tailf:cli-no-name-on-delete;
              tailf:cli-no-value-on-delete;
              type enumeration {
                enum "loop-timed";
                enum "node-timed";
              }
            }
            leaf encap-type {
              tailf:info
                "Configure an encap method";
              tailf:cli-no-value-on-delete;
              type enumeration {
                enum "atm";
                enum "bcp-null";
                enum "bcp-dot1q";
                enum "ipcp";
                enum "ppp-auto";
                enum "frame-relay";
                enum "wan-mirror";
                enum "cisco-hdlc";
                enum "cem";
              }
            }
            container ppp {
              tailf:info
                "Configure the LCP operational parameters";
              tailf:cli-add-mode;
              leaf ber-sf-link-down {
                tailf:info
                  "Enable/Disable port down on BER-SF alarm";
                type empty;
              }
            }
            leaf timeslots {
              tailf:info
                "timeslot range [1..24] (e.g. 1-10,21,23)";
              tailf:cli-no-value-on-delete;
              type string;
            }
            leaf shutdown {
              tailf:cli-boolean-no;
              default "true";
              type boolean;
            }
          }
          leaf clock-source {
            tailf:info
              "Configure the clock for transmitted data";
            tailf:cli-no-value-on-delete;
            type enumeration {
              enum "loop-timed";
              enum "node-timed";
              enum "adaptive";
              enum "differential";
            }
          }
          leaf framing {
            tailf:info
              "Configure the framing for the channel";
            tailf:cli-no-value-on-delete;
            type enumeration {
              enum "esf";
              enum "sf";
              enum "ds1-unframed";
            }
          }
          leaf invert-data {
            tailf:info
              "Enable/disable inverting of data bits";
            type empty;
          }
          leaf loopback {
            tailf:info
              "Activate a loopback on the channel";
            tailf:cli-no-value-on-delete;
            type enumeration {
              enum "line";
              enum "internal";
              enum "fdl-ansi";
              enum "fdl-bellcore";
              enum "payload-ansi";
              enum "inband-ansi";
              enum "inband-bellcore";
            }
          }
          leaf remote-loop-respond {
            tailf:info
              "Enable/disable response to remote loop";
            type empty;
          }
          leaf report-alarm {
            tailf:info
              "Enable/disable logging of alarms";
            tailf:cli-no-value-on-delete;
            type enumeration {
              enum "ais";
              enum "los";
              enum "oof";
              enum "rai";
              enum "looped";
              enum "ber-sd";
              enum "ber-sf";
            }
          }
          leaf signal-mode {
            tailf:info
              "Activate the signal-mode on the channel";
            tailf:cli-no-value-on-delete;
            type enumeration {
              enum "cas";
            }
          }
          container threshold {
            tailf:info
              "Configure BER signal degradation failure thresholds";
            tailf:cli-embed-no-on-delete;
            tailf:cli-compact-syntax;
            tailf:cli-sequence-commands;
            leaf value {
              tailf:cli-no-value-on-delete;
              type enumeration {
                enum "ber-sd";
                enum "ber-sf";
              }
            }
            leaf rate {
              tailf:info
                "Number of errors in millions";
              tailf:cli-no-value-on-delete;
              type enumeration {
                enum "1";
                enum "5";
                enum "10";
                enum "50";
                enum "100";
              }
            }
          }
          leaf shutdown {
            tailf:info
              "Administratively enable/disable the channel";
            tailf:cli-boolean-no;
            default "true";
            type boolean;
          }
        }
        list ds3 {
          tailf:info
            "Configure DS3 channel parameters";
          tailf:cli-embed-no-on-delete;
          key "ds3-id";
          leaf ds3-id {
            tailf:info
              "ds1-number(1-28)|ds1-sonet-sdh-index";
            type string;
          }
          container bert {
            tailf:info
              "Start/Stop a Bit Error Rate Test (BERT)";
            tailf:cli-embed-no-on-delete;
            tailf:cli-compact-syntax;
            tailf:cli-sequence-commands;
            leaf value {
              tailf:cli-no-value-on-delete;
              type enumeration {
                enum "2e3";
                enum "2e9";
                enum "2e11";
                enum "2e15";
                enum "2e20";
                enum "2e20q";
                enum "2e23";
                enum "ones";
                enum "zeros";
                enum "alternating";
              }
            }
          }
          leaf channelized {
            tailf:info
              "Specify if the DS3 port is channelized";
            tailf:cli-no-value-on-delete;
            type enumeration {
              enum "ds1";
              enum "e1";
            }
          }
          leaf clock-source {
            tailf:info
              "Configure the clock for transmitted data";
            tailf:cli-no-name-on-delete;
            tailf:cli-no-value-on-delete;
            type enumeration {
              enum "loop-timed";
              enum "node-timed";
            }
          }
          leaf encap-type {
            tailf:info
              "Configure an encap method";
            tailf:cli-no-value-on-delete;
            type enumeration {
              enum "atm";
              enum "bcp-null";
              enum "bcp-dot1q";
              enum "ipcp";
              enum "ppp-auto";
              enum "frame-relay";
              enum "wan-mirror";
              enum "cisco-hdlc";
              enum "cem";
            }
          }
          leaf shutdown {
            tailf:info
              "Administratively enable/disable the port";
            tailf:cli-boolean-no;
            default "true";
            type boolean;
          }
        }
        leaf lbo {
          tailf:info
            "Configure the transmitter attenuation for a long buildout";
          tailf:cli-no-value-on-delete;
          type enumeration {
            enum "0dB";
            enum "-7.5dB";
            enum "-15.0dB";
            enum "-22.5dB";
          }
        }
        leaf length {
          tailf:info
            "Configure the cable length for a short buildout";
          tailf:cli-no-value-on-delete;
          type enumeration {
            enum "133";
            enum "266";
            enum "399";
            enum "533";
            enum "655";
          }
        }
      }
      leaf shutdown {
        tailf:cli-boolean-no;
        default "true";
        type boolean;
      }
    }
    container qos {
      tailf:ncs-device-type "cli-ned";
      tailf:display-when "not(../../ncs:module) or ../../ncs:module[ncs:name='tailf-ned-alu-sr']";
      tailf:info
        "Configure QoS policies";
      tailf:cli-add-mode;
      list fabric-profile {
        tailf:info
          "Configure fabric-profile policy";
        tailf:cli-recursive-delete;
        tailf:cli-embed-no-on-delete;
        key "policy-id";
        leaf policy-id {
          type uint16 {
            range "1..256";
          }
        }
        leaf mode {
          tailf:info
            "Specify mode of profile";
          tailf:cli-drop-node-name;
          tailf:cli-no-value-on-delete;
          tailf:cli-hide-in-submode;
          type enumeration {
            enum "aggregate-mode";
            enum "destination-mode";
          }
        }
        leaf aggregate-rate {
          tailf:info
            "Configure rate in aggregate mode";
          tailf:cli-no-value-on-delete;
          type union {
            type enumeration {
              enum "default";
            }
            type uint32 {
              range "1..10000000";
            }
          }
        }
        leaf description {
          tailf:info
            "Description for this policy";
          tailf:cli-no-value-on-delete;
          type string;
        }
        list dest-mda {
          tailf:info
            "Configure a destination mda shaping policy";
          key "id";
          leaf id {
            type union {
              type enumeration {
                enum "multipoint";
              }
              type uint32;
            }
          }
          leaf rate {
            tailf:info
              "Specify rate to destination MDA";
            type union {
              type enumeration {
                enum "default";
              }
              type uint32 {
                range "1..10000000";
              }
            }
          }
        }
      }
      list network-queue {
        tailf:cli-embed-no-on-delete;
        tailf:callpoint network-queue-hook {
          tailf:set-hook node;
        }
        key "network-queue-name";
        leaf network-queue-name {
          type string;
        }
        leaf description {
          tailf:cli-embed-no-on-delete;
          tailf:cli-no-value-on-delete;
          type string;
        }
        list queue {
          key "id";
          leaf id {
            type uint32;
          }
          leaf multipoint {
            tailf:cli-hide-in-submode;
            tailf:cli-no-name-on-delete;
            type empty;
          }
          leaf queue-type {
            tailf:cli-drop-node-name;
            tailf:cli-hide-in-submode;
            tailf:cli-no-value-on-delete;
            type enumeration {
              enum "expedite";
              enum "best-effort";
              enum "auto-expedite";
            }
          }
          leaf mbs {
            tailf:info
              "Specify MBS";
            default "50";
            type decimal64 {
              fraction-digits 2;
              range "0..100";
            }
          }
          leaf cbs {
            tailf:info
              "Specify CBS";
            type decimal64 {
              fraction-digits 2;
              range "0..100";
            }
          }
          leaf high-prio-only {
            tailf:info
              "Specify high priority only burst size";
            default "10";
            type union {
              type enumeration {
                enum "default";
              }
              type uint8;
            }
          }
          container rate {
            tailf:info
              "Specify rates (CIR and PIR)";
            tailf:cli-compact-syntax;
            tailf:cli-sequence-commands;
            leaf percent {
              tailf:cli-drop-node-name;
              type uint8 {
                range "0..100";
              }
            }
            leaf cir {
              type uint8 {
                range "0..100";
              }
            }
          }
          container port-parent {
            presence "present";
            tailf:info
              "Specify the port-scheduler to which this queue feeds";
            tailf:cli-compact-syntax;
            tailf:cli-embed-no-on-delete;
            leaf weight {
              tailf:cli-no-name-on-delete;
              tailf:cli-no-value-on-delete;
              type uint8 {
                range "0..100";
              }
            }
            leaf level {
              tailf:cli-no-name-on-delete;
              tailf:cli-no-value-on-delete;
              type uint8 {
                range "1..8";
              }
            }
            leaf cir-weight {
              tailf:cli-no-name-on-delete;
              tailf:cli-no-value-on-delete;
              type uint8 {
                range "0..100";
              }
            }
            leaf cir-level {
              tailf:cli-no-name-on-delete;
              tailf:cli-no-value-on-delete;
              type uint8 {
                range "0..8";
              }
            }
          }
        }
        list fc {
          key "id";
          leaf id {
            type string;
          }
          leaf multicast-queue {
            type uint8;
          }
          leaf queue {
            type uint8;
          }
          container egress-hsmda {
            tailf:cli-add-mode;
            leaf queue {
              type uint8;
            }
          }
        }
      }
      container queue-group-templates {
        tailf:info
          "Configure QoS queue groups";
        tailf:cli-add-mode;
        container egress {
          tailf:info
            "Configure QoS egress queue groups";
          tailf:cli-add-mode;
          list queue-group {
            tailf:info
              "Configure QoS egress queue-group";
            tailf:cli-embed-no-on-delete;
            key "queue-group-name";
            uses queue-group-template-entry;
          }
        }
        container ingress {
          tailf:info
            "Configure QoS ingress queue groups";
          tailf:cli-add-mode;
          list queue-group {
            tailf:info
              "Configure QoS ingress queue-group";
            tailf:cli-embed-no-on-delete;
            key "queue-group-name";
            uses queue-group-template-entry;
          }
        }
      }
      list scheduler-policy {
        tailf:cli-embed-no-on-delete;
        key "scheduler-policy-name";
        leaf scheduler-policy-name {
          type string;
        }
        leaf description {
          tailf:cli-no-value-on-delete;
          type string;
        }
        leaf frame-based-accounting {
          type empty;
        }
        list tier {
          tailf:cli-recursive-delete;
          tailf:cli-embed-no-on-delete;
          key "tier";
          leaf tier {
            type string;
          }
          list scheduler {
            tailf:cli-recursive-delete;
            tailf:cli-embed-no-on-delete;
            key "scheduler-name";
            leaf scheduler-name {
              type string;
            }
            leaf description {
              tailf:cli-embed-no-on-delete;
              tailf:cli-no-value-on-delete;
              type string;
            }
            container parent {
              presence "present";
              tailf:cli-compact-syntax;
              tailf:cli-full-no;
              tailf:cli-recursive-delete;
              tailf:cli-embed-no-on-delete;
              leaf scheduler-name {
                tailf:cli-drop-node-name;
                tailf:cli-no-value-on-delete;
                tailf:cli-delete-container-on-delete;
                type leafref {
                  path "/ncs:devices/ncs:device/ncs:config/alu:qos/scheduler-policy/tier/scheduler/scheduler-name" {
                    tailf:xpath-root 3;
                  }
                }
              }
              leaf weight {
                tailf:cli-no-name-on-delete;
                tailf:cli-no-value-on-delete;
                type string;
              }
              leaf level {
                tailf:cli-no-name-on-delete;
                tailf:cli-no-value-on-delete;
                type string;
              }
              leaf cir-weight {
                tailf:cli-no-name-on-delete;
                tailf:cli-no-value-on-delete;
                type string;
              }
              leaf cir-level {
                tailf:cli-no-name-on-delete;
                tailf:cli-no-value-on-delete;
                type string;
              }
            }
            container port-parent {
              presence "present";
              tailf:cli-compact-syntax;
              leaf weight {
                tailf:cli-no-name-on-delete;
                tailf:cli-no-value-on-delete;
                type string;
              }
              leaf level {
                tailf:cli-no-name-on-delete;
                tailf:cli-no-value-on-delete;
                type string;
              }
              leaf cir-weight {
                tailf:cli-no-name-on-delete;
                tailf:cli-no-value-on-delete;
                type string;
              }
              leaf cir-level {
                tailf:cli-no-name-on-delete;
                tailf:cli-no-value-on-delete;
                type string;
              }
            }
            container rate {
              presence "present";
              tailf:cli-sequence-commands;
              tailf:cli-compact-syntax;
              tailf:cli-full-no;
              tailf:cli-recursive-delete;
              tailf:cli-embed-no-on-delete;
              leaf pir-rate {
                tailf:cli-drop-node-name;
                tailf:cli-delete-container-on-delete;
                mandatory true;
                type string;
              }
              leaf cir {
                tailf:cli-no-name-on-delete;
                tailf:cli-no-value-on-delete;
                type string;
              }
            }
            container mbs {
              tailf:cli-compact-syntax;
              leaf size {
                tailf:cli-drop-node-name;
                type uint32 {
                  range "0..4194304";
                }
              }
              leaf unit {
                tailf:cli-drop-node-name;
                type enumeration {
                  enum "bytes";
                  enum "kilobytes";
                }
              }
            }
          }
        }
      }
      list shared-queue {
        tailf:cli-recursive-delete;
        tailf:cli-embed-no-on-delete;
        key "policy-name";
        leaf policy-name {
          type string;
        }
        leaf description {
          tailf:cli-embed-no-on-delete;
          tailf:cli-no-value-on-delete;
          type string;
        }
        container fc {
          presence "present";
          tailf:cli-sequence-commands;
          tailf:cli-compact-syntax;
          tailf:cli-full-no;
          tailf:cli-recursive-delete;
          tailf:cli-embed-no-on-delete;
          leaf fc-name {
            tailf:cli-drop-node-name;
            tailf:cli-delete-container-on-delete;
            mandatory true;
            type string;
          }
          leaf broadcast-queue {
            type string;
          }
          leaf multicast-queue {
            type string;
          }
          leaf queue {
            type string;
          }
          leaf unknown-queue {
            type string;
          }
        }
        list queue {
          tailf:cli-recursive-delete;
          tailf:cli-embed-no-on-delete;
          key "queue-id";
          leaf queue-id {
            type string;
          }
          leaf queue-type {
            tailf:cli-hide-in-submode;
            tailf:cli-drop-node-name;
            tailf:cli-no-name-on-delete;
            type string;
          }
          leaf multipoint {
            tailf:cli-hide-in-submode;
            type empty;
          }
          leaf cbs {
            type string;
          }
          leaf high-prio-only {
            type string;
          }
          leaf mbs {
            type string;
          }
          leaf pool {
            type string;
          }
          container rate {
            presence "present";
            tailf:cli-sequence-commands;
            tailf:cli-compact-syntax;
            tailf:cli-full-no;
            tailf:cli-recursive-delete;
            tailf:cli-embed-no-on-delete;
            leaf percent {
              tailf:cli-drop-node-name;
              tailf:cli-delete-container-on-delete;
              mandatory true;
              type string;
            }
            leaf cir {
              tailf:cli-hide-in-submode;
              type string;
            }
          }
        }
      }
      list mpls-lsp-exp-profile-map {
        tailf:info
          "Configure mpls-lsp-exp-profile-map policy";
        tailf:cli-embed-no-on-delete;
        key "policy-id";
        leaf policy-id {
          type uint16 {
            range "1..65535";
          }
        }
        leaf description {
          tailf:cli-embed-no-on-delete;
          tailf:cli-no-value-on-delete;
          type string;
        }
        container lsp-exp {
          tailf:cli-embed-no-on-delete;
          leaf lsp-exp-value {
            tailf:cli-drop-node-name;
            tailf:cli-no-value-on-delete;
            type uint8 {
              range "0..7";
            }
          }
          leaf profile {
            tailf:cli-no-name-on-delete;
            tailf:cli-no-value-on-delete;
            type enumeration {
              enum "in";
              enum "out";
            }
          }
        }
      }
      list sap-egress {
        tailf:cli-embed-no-on-delete;
        tailf:cli-diff-dependency "/alu:qos/scheduler-policy" {
          tailf:xpath-root 3;
        }
        key "policy-id";
        leaf policy-id {
          type uint16 {
            range "1 .. 65535";
            tailf:info
              "<policy-id>;;[1..65535]";
          }
        }
        leaf policy-name {
          tailf:cli-no-value-on-delete;
          type string;
        }
        leaf description {
          tailf:cli-embed-no-on-delete;
          tailf:cli-no-value-on-delete;
          type string;
        }
        list queue {
          tailf:cli-embed-no-on-delete;
          key "queue-id";
          leaf queue-id {
            type string;
          }
          leaf queue-type {
            tailf:cli-hide-in-submode;
            tailf:cli-drop-node-name;
            tailf:cli-no-name-on-delete;
            type enumeration {
              enum "expedite";
              enum "best-effort";
              enum "auto-expedite";
            }
          }
          container adaptation-rule {
            tailf:info
              "Specify the CIR and PIR adaptation rules";
            tailf:cli-compact-syntax;
            leaf pir {
              tailf:cli-no-name-on-delete;
              tailf:cli-no-value-on-delete;
              type enumeration {
                enum "max";
                enum "min";
                enum "closest";
              }
            }
            leaf cir {
              tailf:cli-no-name-on-delete;
              tailf:cli-no-value-on-delete;
              type enumeration {
                enum "max";
                enum "min";
                enum "closest";
              }
            }
          }
          container parent {
            tailf:cli-compact-syntax;
            tailf:cli-sequence-commands {
              tailf:cli-reset-all-siblings;
            }
            leaf scheduler-name {
              tailf:cli-drop-node-name;
              tailf:cli-no-value-on-delete;
              type string;
            }
            leaf weight {
              tailf:cli-break-sequence-commands;
              tailf:cli-no-value-on-delete;
              tailf:cli-no-name-on-delete;
              type uint8 {
                range "0..100";
              }
            }
            leaf level {
              tailf:cli-no-value-on-delete;
              tailf:cli-no-name-on-delete;
              type uint8 {
                range "1..8";
              }
            }
            leaf cir-weight {
              tailf:cli-no-value-on-delete;
              tailf:cli-no-name-on-delete;
              type uint8 {
                range "0..100";
              }
            }
            leaf cir-level {
              tailf:cli-no-value-on-delete;
              tailf:cli-no-name-on-delete;
              type uint8 {
                range "0..8";
              }
            }
          }
          container port-parent {
            tailf:cli-compact-syntax;
            leaf weight {
              type uint8 {
                range "0..100";
              }
            }
            leaf level {
              type uint8 {
                range "1..8";
              }
            }
            leaf cir-weight {
              type uint8 {
                range "0..100";
              }
            }
            leaf cir-level {
              type uint8 {
                range "0..8";
              }
            }
          }
          container rate {
            tailf:cli-sequence-commands;
            tailf:cli-compact-syntax;
            tailf:cli-full-no;
            tailf:cli-embed-no-on-delete;
            leaf pir-rate {
              tailf:cli-drop-node-name;
              tailf:cli-delete-container-on-delete;
              type union {
                type enumeration {
                  enum "max";
                }
                type uint32 {
                  range "1..100000000";
                }
              }
            }
            leaf cir {
              type union {
                type enumeration {
                  enum "max";
                }
                type uint32 {
                  range "0..100000000";
                }
              }
            }
          }
          container cbs {
            tailf:cli-compact-syntax;
            leaf size {
              tailf:cli-drop-node-name;
              tailf:cli-no-value-on-delete;
              type uint32 {
                range "0..4194304";
              }
            }
          }
          container mbs {
            tailf:cli-compact-syntax;
            leaf size {
              tailf:cli-drop-node-name;
              tailf:cli-no-value-on-delete;
              type uint32 {
                range "0..4194304";
              }
            }
            leaf unit {
              tailf:cli-drop-node-name;
              type enumeration {
                enum "bytes";
                enum "kilobytes";
              }
            }
          }
          container burst-limit {
            tailf:info
              "Specify burst-limit";
            tailf:cli-embed-no-on-delete;
            tailf:cli-compact-syntax;
            tailf:cli-sequence-commands;
            leaf size {
              tailf:cli-drop-node-name;
              tailf:cli-no-value-on-delete;
              type union {
                type uint32 {
                  range "0..4194304";
                }
                type enumeration {
                  enum "default";
                }
              }
            }
            leaf unit {
              tailf:cli-drop-node-name;
              tailf:cli-no-value-on-delete;
              type enumeration {
                enum "bytes";
                enum "kilobytes";
              }
            }
          }
          container xp-specific {
            tailf:info
              "Configure IOM3-XP specific information";
            tailf:cli-add-mode;
            container wred-queue {
              tailf:info
                "Configure WRED queue";
              tailf:cli-embed-no-on-delete;
              tailf:cli-compact-syntax;
              tailf:cli-sequence-commands;
              leaf policy {
                tailf:info
                  "max 32 chars;;slope-policy-name";
                tailf:cli-no-value-on-delete;
                tailf:cli-no-name-on-delete;
                type string;
              }
            }
            container packet-byte-offset {
              tailf:info
                "Specify packet byte offset";
              tailf:cli-embed-no-on-delete;
              tailf:cli-compact-syntax;
              tailf:cli-sequence-commands;
              choice a {
                leaf add {
                  type uint8 {
                    range "0..32";
                  }
                }
                leaf subtract {
                  type uint8 {
                    range "0..64";
                  }
                }
              }
            }
          }
        }
        list fc {
          tailf:cli-embed-no-on-delete;
          key "fc-name";
          leaf fc-name {
            type string;
          }
          leaf queue {
            type string;
          }
          container dot1p {
            tailf:cli-compact-syntax;
            tailf:cli-sequence-commands;
            choice dot1p-choice {
              case a {
                leaf dot1p-value {
                  tailf:cli-drop-node-name;
                  type uint8 {
                    range "0..7";
                  }
                }
              }
              case b {
                leaf in-profile {
                  type uint8 {
                    range "0..7";
                  }
                }
                leaf out-profile {
                  type uint8 {
                    range "0..7";
                  }
                }
              }
            }
          }
        }
        container ip-criteria {
          tailf:cli-add-mode;
          uses ip-criteria-grouping;
        }
        container ipv6-criteria {
          tailf:cli-add-mode;
          uses ipv6-criteria-grouping;
        }
        list dscp {
          tailf:cli-suppress-mode;
          key "id";
          tailf:cli-compact-syntax;
          leaf id {
            type dscp-type;
          }
          leaf fc {
            type string;
          }
          leaf priority {
            type enumeration {
              enum "high";
              enum "low";
            }
          }
        }
      }
      list sap-ingress {
        tailf:cli-embed-no-on-delete;
        tailf:cli-diff-dependency "/alu:qos/scheduler-policy" {
          tailf:xpath-root 3;
        }
        key "policy-id";
        leaf policy-id {
          type uint16 {
            range "1 .. 65535";
            tailf:info
              "<policy-id>;;[1..65535]";
          }
        }
        leaf description {
          tailf:cli-embed-no-on-delete;
          tailf:cli-no-value-on-delete;
          type string;
        }
        leaf policy-name {
          tailf:cli-no-value-on-delete;
          type string;
        }
        list meter {
          tailf:info
            "Configure a meter";
          tailf:cli-embed-no-on-delete;
          key "meter-id";
          uses meter-grouping;
        }
        container num-qos-classifiers {
          tailf:info
            "Configure number of classfiers and meters for this policy";
          tailf:cli-embed-no-on-delete;
          tailf:cli-compact-syntax;
          leaf num-resources {
            tailf:cli-drop-node-name;
            tailf:cli-no-value-on-delete;
            type uint16 {
              range "1..256";
            }
          }
          leaf keyword {
            tailf:cli-drop-node-name;
            tailf:cli-no-value-on-delete;
            type enumeration {
              enum "ipv6";
              enum "no-ipv6";
            }
          }
        }
        list prec {
          key "ip-prec-value";
          tailf:info
            "Specify IP precedence mappings";
          tailf:cli-compact-syntax;
          tailf:cli-suppress-mode;
          leaf ip-prec-value {
            tailf:cli-drop-node-name;
            type uint16 {
              range "0..7";
            }
          }
          leaf fc {
            type enumeration {
              enum "be";
              enum "l2";
              enum "af";
              enum "l1";
              enum "h2";
              enum "ef";
              enum "h1";
              enum "nc";
            }
          }
          leaf priority {
            type enumeration {
              enum "low";
              enum "high";
            }
          }
        }
        list queue {
          tailf:cli-embed-no-on-delete;
          key "queue-id";
          leaf queue-id {
            type string;
          }
          leaf multipoint {
            tailf:cli-hide-in-submode;
            type empty;
          }
          leaf queue-type {
            tailf:cli-hide-in-submode;
            tailf:cli-drop-node-name;
            tailf:cli-no-name-on-delete;
            type string;
          }
          leaf queue-mode {
            tailf:cli-hide-in-submode;
            tailf:cli-drop-node-name;
            tailf:cli-no-name-on-delete;
            type string;
          }
          container adaptation-rule {
            tailf:info
              "Specify the CIR and PIR adaptation rules";
            tailf:cli-compact-syntax;
            leaf pir {
              tailf:cli-no-name-on-delete;
              tailf:cli-no-value-on-delete;
              type enumeration {
                enum "max";
                enum "min";
                enum "closest";
              }
            }
            leaf cir {
              tailf:cli-no-name-on-delete;
              tailf:cli-no-value-on-delete;
              type enumeration {
                enum "max";
                enum "min";
                enum "closest";
              }
            }
          }
          container parent {
            tailf:cli-compact-syntax;
            tailf:cli-sequence-commands {
              tailf:cli-reset-all-siblings;
            }
            leaf scheduler-name {
              tailf:cli-drop-node-name;
              tailf:cli-no-value-on-delete;
              type string;
            }
            leaf weight {
              tailf:cli-break-sequence-commands;
              tailf:cli-no-value-on-delete;
              tailf:cli-no-name-on-delete;
              type uint8 {
                range "0..100";
              }
            }
            leaf level {
              tailf:cli-no-value-on-delete;
              tailf:cli-no-name-on-delete;
              type uint8 {
                range "1..8";
              }
            }
            leaf cir-weight {
              tailf:cli-no-value-on-delete;
              tailf:cli-no-name-on-delete;
              type uint8 {
                range "0..100";
              }
            }
            leaf cir-level {
              tailf:cli-no-value-on-delete;
              tailf:cli-no-name-on-delete;
              type uint8 {
                range "0..8";
              }
            }
          }
          container cbs {
            tailf:cli-compact-syntax;
            leaf size {
              tailf:cli-drop-node-name;
              tailf:cli-no-value-on-delete;
              type uint32 {
                range "0..4194304";
              }
            }
          }
          container mbs {
            tailf:cli-compact-syntax;
            leaf size {
              tailf:cli-drop-node-name;
              tailf:cli-no-value-on-delete;
              type uint32 {
                range "0..4194304";
              }
            }
            leaf unit {
              tailf:cli-drop-node-name;
              type enumeration {
                enum "bytes";
                enum "kilobytes";
              }
            }
          }
          container rate {
            tailf:cli-sequence-commands;
            tailf:cli-compact-syntax;
            tailf:cli-full-no;
            tailf:cli-embed-no-on-delete;
            leaf pir-rate {
              tailf:cli-drop-node-name;
              tailf:cli-delete-container-on-delete;
              type string;
            }
            leaf cir {
              type string;
            }
          }
        }
        list fc {
          tailf:cli-embed-no-on-delete;
          key "fc-name";
          leaf fc-name {
            type string;
          }
          leaf queue {
            type string;
          }
          container broadcast-queue {
            tailf:cli-compact-syntax;
            tailf:cli-sequence-commands;
            leaf id {
              tailf:cli-drop-node-name;
              type uint8 {
                range "1..32";
              }
            }
            leaf group {
              type string;
            }
          }
          container multicast-queue {
            tailf:cli-compact-syntax;
            tailf:cli-sequence-commands;
            leaf id {
              tailf:cli-drop-node-name;
              type uint8 {
                range "1..32";
              }
            }
            leaf group {
              type string;
            }
          }
          container unknown-queue {
            tailf:cli-compact-syntax;
            tailf:cli-sequence-commands;
            leaf id {
              tailf:cli-drop-node-name;
              type uint8 {
                range "1..32";
              }
            }
            leaf group {
              type string;
            }
          }
          leaf broadcast-meter {
            tailf:info
              "Specify the broadcast-meter";
            tailf:cli-embed-no-on-delete;
            tailf:cli-no-value-on-delete;
            type leafref {
              path "../../meter/meter-id";
            }
          }
          leaf meter {
            tailf:info
              "Specify the unicast-meter";
            tailf:cli-embed-no-on-delete;
            tailf:cli-no-value-on-delete;
            type leafref {
              path "../../meter/meter-id";
            }
          }
          leaf multicast-meter {
            tailf:info
              "Specify the multicast-meter";
            tailf:cli-embed-no-on-delete;
            tailf:cli-no-value-on-delete;
            type leafref {
              path "../../meter/meter-id";
            }
          }
          leaf unknown-meter {
            tailf:info
              "Specify the unknown-meter";
            tailf:cli-embed-no-on-delete;
            tailf:cli-no-value-on-delete;
            type leafref {
              path "../../meter/meter-id";
            }
          }
          container in-remark {
            choice remark-choice {
              leaf dscp {
                type dscp-type;
              }
              leaf prec {
                type uint8 {
                  range "0..7";
                }
              }
            }
          }
          container out-remark {
            choice remark-choice {
              leaf dscp {
                type dscp-type;
              }
              leaf prec {
                type uint8 {
                  range "0..7";
                }
              }
            }
          }
          container policer {
            tailf:cli-compact-syntax;
            tailf:cli-sequence-commands;
            leaf id {
              tailf:cli-drop-node-name;
              type uint8 {
                range "1..32";
              }
            }
            leaf fp-redirect-group {
              tailf:cli-drop-node-name;
              type string;
            }
          }
        }
        container ip-criteria {
          tailf:cli-add-mode;
          uses ip-criteria-grouping;
        }
        container ipv6-criteria {
          tailf:cli-add-mode;
          uses ipv6-criteria-grouping;
        }
        leaf default-fc {
          tailf:info
            "Configure default forwarding class for this policy";
          type string;
        }
        leaf default-priority {
          tailf:info
            "Configure default priority for this policy";
          type enumeration {
            enum "low";
            enum "high";
          }
        }
        list dot1p {
          tailf:cli-suppress-mode;
          key "id";
          tailf:cli-compact-syntax;
          leaf id {
            type uint8 {
              range "0..7";
            }
          }
          leaf fc {
            type string;
          }
          leaf priority {
            type enumeration {
              enum "high";
              enum "low";
            }
          }
        }
        list dscp {
          tailf:cli-suppress-mode;
          key "id";
          tailf:cli-compact-syntax;
          leaf id {
            type dscp-type;
          }
          leaf fc {
            type string;
          }
          leaf priority {
            type enumeration {
              enum "high";
              enum "low";
            }
          }
        }
        list policer {
          tailf:cli-embed-no-on-delete;
          key "id";
          leaf id {
            type uint8 {
              range "1..32";
            }
          }
          container rate {
            tailf:cli-compact-syntax;
            leaf pir {
              tailf:cli-drop-node-name;
              type union {
                type uint32;
                type enumeration {
                  enum "max";
                }
              }
            }
            leaf cir {
              type union {
                type uint32;
                type enumeration {
                  enum "max";
                }
              }
            }
          }
          container cbs {
            tailf:cli-compact-syntax;
            leaf size {
              tailf:cli-drop-node-name;
              tailf:cli-no-value-on-delete;
              type uint32 {
                range "0..4194304";
              }
            }
          }
          container mbs {
            tailf:cli-compact-syntax;
            leaf size {
              tailf:cli-drop-node-name;
              tailf:cli-no-value-on-delete;
              type uint32 {
                range "0..4194304";
              }
            }
            leaf unit {
              tailf:cli-drop-node-name;
              type enumeration {
                enum "bytes";
                enum "kilobytes";
              }
            }
          }
        }
      }
      list network {
        tailf:cli-embed-no-on-delete;
        key "id";
        leaf id {
          type uint16;
        }
        leaf network-policy-type {
          tailf:cli-hide-in-submode;
          tailf:cli-no-name-on-delete;
          tailf:cli-no-value-on-delete;
          type enumeration {
            enum "ip-interface";
            enum "port";
          }
        }
        leaf description {
          tailf:cli-embed-no-on-delete;
          tailf:cli-no-value-on-delete;
          type string;
        }
        container ingress {
          tailf:cli-add-mode;
          list dscp {
            tailf:cli-compact-syntax;
            tailf:cli-suppress-mode;
            key "id";
            leaf id {
              type dscp-type;
            }
            leaf fc {
              tailf:cli-no-name-on-delete;
              tailf:cli-no-value-on-delete;
              type string;
            }
            leaf profile {
              tailf:cli-no-name-on-delete;
              tailf:cli-no-value-on-delete;
              type enumeration {
                enum "in";
                enum "out";
              }
            }
          }
          list lsp-exp {
            tailf:cli-compact-syntax;
            tailf:cli-suppress-mode;
            key "id";
            leaf id {
              type uint8 {
                range "0..7";
              }
            }
            leaf fc {
              type enumeration {
                enum "be";
                enum "l2";
                enum "af";
                enum "l1";
                enum "h2";
                enum "ef";
                enum "h1";
                enum "nc";
              }
            }
            leaf profile {
              type enumeration {
                enum "in";
                enum "out";
              }
            }
          }
          container default-action {
            tailf:cli-compact-syntax;
            leaf fc {
              type enumeration {
                enum "be";
                enum "l2";
                enum "af";
                enum "l1";
                enum "h2";
                enum "ef";
                enum "h1";
                enum "nc";
              }
            }
            leaf profile {
              type enumeration {
                enum "in";
                enum "out";
              }
            }
          }
          list meter {
            tailf:info
              "Configure a meter";
            tailf:cli-embed-no-on-delete;
            key "meter-id";
            uses meter-grouping;
          }
          leaf mpls-lsp-exp-profile {
            tailf:info
              "Configure mpls-lsp-exp-profile policy";
            tailf:cli-no-value-on-delete;
            type uint16 {
              range "1..65535";
            }
          }
          list fc {
            tailf:info
              "Configure forwarding-class to meter mappings";
            tailf:cli-embed-no-on-delete;
            key "class";
            leaf class {
              type string;
            }
            leaf meter {
              tailf:cli-embed-no-on-delete;
              tailf:cli-no-value-on-delete;
              type uint8 {
                range "1..12";
              }
            }
            leaf multicast-meter {
              tailf:cli-embed-no-on-delete;
              tailf:cli-no-value-on-delete;
              type uint8 {
                range "1..12";
              }
            }
          }
        }
        container egress {
          tailf:cli-add-mode;
          list fc {
            key "id";
            leaf id {
              type enumeration {
                enum "be";
                enum "l2";
                enum "af";
                enum "l1";
                enum "h2";
                enum "ef";
                enum "h1";
                enum "nc";
              }
            }
            leaf dscp-in-profile {
              type dscp-type;
            }
            leaf dscp-out-profile {
              type dscp-type;
            }
            leaf lsp-exp-in-profile {
              type uint8 {
                range "0..7";
              }
            }
            leaf lsp-exp-out-profile {
              type uint8 {
                range "0..7";
              }
            }
            leaf dot1p-in-profile {
              type uint8 {
                range "0..7";
              }
            }
            leaf dot1p-out-profile {
              type uint8 {
                range "0..7";
              }
            }
          }
          container remarking {
            presence "true";
            leaf force {
              type empty;
            }
          }
          container prec {
            tailf:cli-compact-syntax;
            leaf prec-value {
              tailf:cli-drop-node-name;
              type uint8 {
                range "0..7";
              }
            }
            leaf fc {
              type enumeration {
                enum "be";
                enum "l2";
                enum "af";
                enum "l1";
                enum "h2";
                enum "ef";
                enum "h1";
                enum "nc";
              }
            }
            leaf profile {
              type enumeration {
                enum "in";
                enum "out";
              }
            }
          }
          list dscp {
            tailf:cli-compact-syntax;
            tailf:cli-suppress-mode;
            key "id";
            leaf id {
              type dscp-type;
            }
            leaf fc {
              tailf:cli-no-name-on-delete;
              tailf:cli-no-value-on-delete;
              type string;
            }
            leaf profile {
              tailf:cli-no-name-on-delete;
              tailf:cli-no-value-on-delete;
              type enumeration {
                enum "in";
                enum "out";
              }
            }
          }
        }
      }
      list slope-policy {
        tailf:info
          "Configure a slope-policy";
        key "name";
        leaf name {
          type string;
        }
        leaf description {
          tailf:info
            "Description for the slope policy policy";
          tailf:cli-no-value-on-delete;
          type string {
            length "1..80";
          }
        }
        container high-slope {
          tailf:info
            "Configure high-prio RED slope parameters";
          tailf:cli-add-mode;
          leaf start-avg {
            tailf:info
              "Configure starting average";
            tailf:cli-no-value-on-delete;
            type uint8 {
              range "0..100";
            }
          }
          leaf max-avg {
            tailf:info
              "Configure max average";
            tailf:cli-no-value-on-delete;
            type uint8 {
              range "0..100";
            }
          }
          leaf max-prob {
            tailf:info
              "Configure max probability";
            tailf:cli-no-value-on-delete;
            type uint8 {
              range "0..100";
            }
          }
          leaf shutdown {
            tailf:info
              "Administratively enable/disable high slope";
            tailf:cli-boolean-no;
            default "true";
            type boolean;
          }
        }
        container low-slope {
          tailf:info
            "Configure low-prio RED slope parameters";
          tailf:cli-add-mode;
          leaf start-avg {
            tailf:info
              "Configure starting average";
            tailf:cli-no-value-on-delete;
            type uint8 {
              range "0..100";
            }
          }
          leaf max-avg {
            tailf:info
              "Configure max average";
            tailf:cli-no-value-on-delete;
            type uint8 {
              range "0..100";
            }
          }
          leaf max-prob {
            tailf:info
              "Configure max probability";
            tailf:cli-no-value-on-delete;
            type uint8 {
              range "0..100";
            }
          }
          leaf shutdown {
            tailf:info
              "Administratively enable/disable low slope";
            tailf:cli-boolean-no;
            default "true";
            type boolean;
          }
        }
      }
      list port-scheduler-policy {
        tailf:info
          "Configure a port scheduler policy";
        key "name";
        leaf name {
          type string;
        }
        leaf description {
          tailf:info
            "Description for this policy";
          tailf:cli-no-value-on-delete;
          type string;
        }
        list level {
          tailf:info
            "Configure priority level parameters";
          tailf:cli-suppress-mode;
          tailf:cli-compact-syntax;
          key "priority-level";
          leaf priority-level {
            type uint8 {
              range "1..8";
            }
          }
          leaf rate {
            type uint32;
          }
          leaf cir {
            type uint32;
          }
        }
        leaf max-rate {
          tailf:info
            "Configure the maximum rate";
          type uint32 {
            range "1..3200000000";
          }
        }
        container orphan-override {
          tailf:info
            "Configure port scheduler policy orphan settings";
          tailf:cli-compact-syntax;
          leaf level {
            type uint8 {
              range "1..8";
            }
          }
        }
      }
      list policer-control-policy {
        tailf:info
          "Configure Qos Policer control Policy";
        tailf:cli-embed-no-on-delete;
        key "name";
        leaf name {
          type string {
            length "1..32";
          }
        }
        leaf description {
          tailf:info
            "Description for this policy";
          tailf:cli-no-value-on-delete;
          type string;
        }
        container root {
          tailf:info
            "Specify Root Configuration";
          tailf:cli-embed-no-on-delete;
          tailf:cli-add-mode;
          leaf max-rate {
            tailf:info
              "Configure Max Rate in kilobits-per-second";
            tailf:cli-no-value-on-delete;
            type union {
              type uint32 {
                range "1..20000000";
              }
              type enumeration {
                enum "max";
              }
            }
          }
        }
        container priority-mbs-thresholds {
          tailf:info
            "Configure priority mbs thresholds";
          tailf:cli-embed-no-on-delete;
          tailf:cli-add-mode;
          container min-thresh-separation {
            tailf:info
              "Configure min threshold separation";
            tailf:cli-sequence-commands;
            tailf:cli-compact-syntax;
            leaf size {
              tailf:cli-drop-node-name;
              tailf:cli-no-value-on-delete;
              type union {
                type uint32 {
                  range "0..4194304";
                }
                type enumeration {
                  enum "default";
                }
              }
            }
            leaf unit {
              tailf:cli-drop-node-name;
              tailf:cli-no-value-on-delete;
              type enumeration {
                enum "bytes";
                enum "kilobytes";
              }
            }
          }
          list priority {
            tailf:info
              "Configure Priority Levels";
            tailf:cli-embed-no-on-delete;
            key "level";
            leaf level {
              type uint8 {
                range "1..8";
              }
            }
            container mbs-contribution {
              tailf:info
                "Configure mbs size";
              tailf:cli-compact-syntax;
              tailf:cli-sequence-commands;
              tailf:cli-embed-no-on-delete;
              leaf size {
                tailf:cli-drop-node-name;
                tailf:cli-no-value-on-delete;
                type union {
                  type uint32 {
                    range "0..4194304";
                  }
                  type enumeration {
                    enum "default";
                  }
                }
              }
              leaf unit {
                tailf:cli-drop-node-name;
                tailf:cli-no-value-on-delete;
                type enumeration {
                  enum "bytes";
                  enum "kilobytes";
                }
              }
              leaf fixed {
                type empty;
              }
            }
          }
        }
      }
    }
    container eth-cfm {
      tailf:ncs-device-type "cli-ned";
      tailf:display-when "not(../../ncs:module) or ../../ncs:module[ncs:name='tailf-ned-alu-sr']";
      tailf:info
        "Configure CFM parameters";
      tailf:cli-add-mode;
      list domain {
        tailf:info
          "Configure Connectivity Fault Management domain";
        tailf:cli-recursive-delete;
        tailf:cli-embed-no-on-delete;
        key "id";
        leaf id {
          tailf:info
            "<md-index>;;<1..4294967295>";
          type uint32 {
            range "1..4294967295";
          }
        }
        leaf format {
          tailf:info
            "<format>;;<dns|mac|none|string>";
          tailf:cli-hide-in-submode;
          tailf:cli-no-name-on-delete;
          tailf:cli-no-value-on-delete;
          type string;
        }
        leaf level {
          tailf:info
            "<level>;;<0..7>";
          tailf:cli-hide-in-submode;
          tailf:cli-no-name-on-delete;
          tailf:cli-no-value-on-delete;
          type uint8 {
            range "0..7";
          }
        }
        leaf name {
          tailf:info
            "<name>;;<string>";
          tailf:cli-hide-in-submode;
          tailf:cli-no-name-on-delete;
          tailf:cli-no-value-on-delete;
          type string;
        }
        list association {
          tailf:info
            "Configure a Maintenance Association for the Domain";
          tailf:cli-recursive-delete;
          tailf:cli-embed-no-on-delete;
          key "ma-index";
          leaf ma-index {
            tailf:info
              "<ma-index>";
            type uint32 {
              range "1..4294967295";
            }
          }
          leaf format {
            tailf:info
              "{icc-based|integer|string|vid|vpn-id}";
            tailf:cli-hide-in-submode;
            tailf:cli-no-name-on-delete;
            tailf:cli-no-value-on-delete;
            type enumeration {
              enum "icc-based";
              enum "integer";
              enum "string";
              enum "vid";
              enum "vpn-id";
            }
          }
          leaf name {
            tailf:info
              "Maintenance Association Name (1..45 characters)";
            tailf:cli-hide-in-submode;
            tailf:cli-no-name-on-delete;
            tailf:cli-no-value-on-delete;
            type string {
              length "1..45";
            }
          }
          container ccm-hold-time {
            tailf:info
              "Configure the CCM interval holding timers";
            tailf:cli-embed-no-on-delete;
            leaf down {
              type uint32;
            }
          }
          leaf ccm-interval {
            tailf:info
              "Configure the CCM transmission interval for all MEPs";
            tailf:cli-embed-no-on-delete;
            type enumeration {
              enum "10ms";
              enum "100ms";
              enum "1";
              enum "10";
              enum "60";
              enum "600";
            }
          }
          container remote-mepid {
            leaf mep-id {
              tailf:info
                "Configure the Remote MEP ID";
              tailf:cli-embed-no-on-delete;
              tailf:cli-drop-node-name;
              type uint16 {
                range "1..8191";
              }
            }
            leaf remote-mac {
              tailf:info
                "xx:xx:xx:xx:xx:xx or default";
              type union {
                type enumeration {
                  enum "default";
                }
                type ieee-mac;
              }
            }
          }
          list bridge-identifier {
            tailf:info
              "Configure the service ID for the association";
            tailf:cli-embed-no-on-delete;
            key "id";
            leaf id {
              type uint32;
            }
            leaf mhf-creation {
              tailf:info
                "Configure the MIP Half Function (MHF)";
              tailf:cli-embed-no-on-delete;
              type enumeration {
                enum "default";
                enum "none";
                enum "explicit";
              }
            }
            leaf vlan {
              tailf:info
                "Configure the Bridge-identifier Primary Vlan-Id";
              tailf:cli-embed-no-on-delete;
              type uint16 {
                range "0..4094";
              }
            }
          }
        }
      }
    }
    container log {
      tailf:ncs-device-type "cli-ned";
      tailf:display-when "not(../../ncs:module) or ../../ncs:module[ncs:name='tailf-ned-alu-sr']";
      tailf:info
        "Event stream logging configuration";
      tailf:cli-add-mode;
      list file-id {
        tailf:cli-embed-no-on-delete;
        key "id";
        leaf id {
          type uint32;
        }
        leaf description {
          type string;
        }
        leaf-list location {
          tailf:cli-flat-list-syntax;
          tailf:cli-no-value-on-delete;
          type string;
        }
        container rollover {
          tailf:cli-embed-no-on-delete;
          tailf:cli-compact-syntax;
          tailf:cli-sequence-commands;
          leaf id {
            tailf:cli-drop-node-name;
            tailf:cli-no-value-on-delete;
            type uint32;
          }
          leaf retention {
            tailf:cli-no-value-on-delete;
            tailf:cli-no-name-on-delete;
            type uint32;
          }
        }
      }
      list accounting-policy {
        tailf:info
          "Configure an accounting-policy";
        key "acct-policy-id";
        leaf acct-policy-id {
          type uint16 {
            range "1..99";
          }
        }
        leaf collection-interval {
          tailf:cli-no-value-on-delete;
          tailf:info
            "Configure the accounting collection interval";
          type uint8 {
            range "0..120";
          }
        }
        leaf description {
          tailf:info
            "Description for this accounting policy";
          tailf:cli-no-value-on-delete;
          type string {
            length "1..80";
          }
        }
        leaf record {
          tailf:info
            "Configure the accounting record type to be forwarded to the configured accounting file";
          type enumeration {
            enum "aa-app-group";
            enum "aa-application";
            enum "aa-partition";
            enum "aa-performance";
            enum "aa-protocol";
            enum "aa-subscriber-application";
            enum "aa-subscriber-protocol";
            enum "combined-ldp-lsp-egress";
            enum "combined-mpls-lsp-egress";
            enum "combined-mpls-lsp-ingress";
            enum "combined-network-ing-egr-octets";
            enum "combined-queue-group";
            enum "combined-sdp-ingress-egress";
            enum "combined-service-ing-egr-octets";
            enum "combined-service-ingress";
            enum "compact-service-ingress-octets";
            enum "complete-pm";
            enum "complete-sdp-ingress-egress";
            enum "complete-service-ingress-egress";
            enum "complete-subscriber-ingress-egress";
            enum "custom-record-aa-sub";
            enum "custom-record-service";
            enum "custom-record-subscriber";
            enum "network-egress-octets";
            enum "network-egress-packets";
            enum "network-ingress-octets";
            enum "network-ingress-packets";
            enum "queue-group-octets";
            enum "queue-group-packets";
            enum "saa";
            enum "service-egress-octets";
            enum "service-egress-packets";
            enum "service-ingress-octets";
            enum "service-ingress-packets";
            enum "video";
            enum "complete-ethernet-port";
            enum "extended-service-ingress-egress";
            enum "complete-network-ing-egr";
          }
        }
        container to {
          tailf:info
            "Specify log destination";
          tailf:cli-compact-syntax;
          leaf destination {
            tailf:cli-drop-node-name;
            type enumeration {
              enum "file";
              enum "no-file";
            }
          }
          leaf log-file-id {
            tailf:cli-drop-node-name;
            when "../destination = 'file'" {
              tailf:xpath-root 3;
            }
            type leafref {
              path "/ncs:devices/ncs:device/ncs:config/alu:log/file-id/id" {
                tailf:xpath-root 3;
              }
            }
          }
        }
        leaf shutdown {
          tailf:cli-boolean-no;
          default "true";
          type boolean;
        }
      }
      list event-control {
        tailf:cli-suppress-mode;
        tailf:cli-embed-no-on-delete;
        tailf:cli-compact-syntax;
        tailf:cli-sequence-commands;
        key "name";
        leaf name {
          type string;
        }
        leaf year {
          tailf:cli-drop-node-name;
          tailf:cli-no-value-on-delete;
          type uint32;
        }
        leaf generate {
          tailf:cli-no-name-on-delete;
          type empty;
        }
        leaf throttle {
          tailf:cli-no-name-on-delete;
          type empty;
        }
      }
      list filter {
        tailf:info
          "Configure an event filter";
        tailf:cli-embed-no-on-delete;
        key "filter-id";
        leaf filter-id {
          type uint16 {
            range "1..1001";
          }
        }
        leaf default-action {
          tailf:info
            "Specify the default action for the event filter";
          tailf:cli-no-value-on-delete;
          type enumeration {
            enum "drop";
            enum "forward";
          }
        }
        leaf description {
          tailf:info
            "Description string for the event filter";
          tailf:cli-no-value-on-delete;
          type string;
        }
        list entry {
          tailf:info
            "Configure an event filter entry";
          tailf:cli-embed-no-on-delete;
          key "entry-id";
          leaf entry-id {
            type uint16 {
              range "1..999";
            }
          }
          leaf action {
            tailf:info
              "Specify the action for this event filter entry";
            tailf:cli-no-value-on-delete;
            type enumeration {
              enum "drop";
              enum "forward";
            }
          }
          leaf description {
            tailf:info
              "Description for this event filter entry";
            tailf:cli-no-value-on-delete;
            type string;
          }
          container match {
            tailf:info
              "Specify match conditions for this event filter entry";
            tailf:cli-embed-no-on-delete;
            tailf:cli-add-mode;
            container application {
              tailf:info
                "Specify application id to match";
              tailf:cli-compact-syntax;
              tailf:cli-sequence-commands;
              tailf:cli-embed-no-on-delete;
              leaf rule {
                tailf:cli-drop-node-name;
                tailf:cli-no-value-on-delete;
                type enumeration {
                  enum "eq";
                  enum "neq";
                }
              }
              leaf application-id {
                tailf:cli-drop-node-name;
                tailf:cli-no-value-on-delete;
                type enumeration {
                  enum "application_assurance";
                  enum "aps";
                  enum "atm";
                  enum "bgp";
                  enum "cflowd";
                  enum "chassis";
                  enum "debug";
                  enum "dhcp";
                  enum "dhcps";
                  enum "diameter";
                  enum "dynsvc";
                  enum "efm_oam";
                  enum "elmi";
                  enum "ering";
                  enum "eth_cfm";
                  enum "etun";
                  enum "filter";
                  enum "gsmp";
                  enum "gmpls";
                  enum "igh";
                  enum "igmp";
                  enum "igmp_snooping";
                  enum "ip";
                  enum "ipsec";
                  enum "isis";
                  enum "l2tp";
                  enum "lag";
                  enum "ldp";
                  enum "li";
                  enum "lldp";
                  enum "lmp";
                  enum "logger";
                  enum "mcpath";
                  enum "mc_redundancy";
                  enum "mirror";
                  enum "mld";
                  enum "mld_snooping";
                  enum "mpls";
                  enum "mpls_tp";
                  enum "msdp";
                  enum "nat";
                  enum "ntp";
                  enum "oam";
                  enum "open_flow";
                  enum "ospf";
                  enum "pim";
                  enum "pim_snooping";
                  enum "port";
                  enum "ppp";
                  enum "pppoe";
                  enum "radius";
                  enum "rip";
                  enum "rip_ng";
                  enum "route_policy";
                  enum "rsvp";
                  enum "security";
                  enum "snmp";
                  enum "stp";
                  enum "svcmgr";
                  enum "system";
                  enum "user";
                  enum "video";
                  enum "vrrp";
                  enum "vrtr";
                  enum "wlan_gw";
                  enum "wpp";
                }
              }
            }
            container message {
              tailf:info
                "Specify pattern to match message";
              tailf:cli-compact-syntax;
              tailf:cli-sequence-commands;
              tailf:cli-embed-no-on-delete;
              leaf rule {
                tailf:cli-drop-node-name;
                tailf:cli-no-value-on-delete;
                type enumeration {
                  enum "eq";
                  enum "neq";
                }
              }
              leaf pattern {
                tailf:cli-no-value-on-delete;
                type string;
              }
              leaf regexp {
                tailf:cli-no-name-on-delete;
                type empty;
              }
            }
            container number {
              tailf:info
                "Specify event-id number to match";
              tailf:cli-compact-syntax;
              tailf:cli-sequence-commands;
              tailf:cli-embed-no-on-delete;
              leaf rule {
                tailf:cli-drop-node-name;
                tailf:cli-no-value-on-delete;
                type enumeration {
                  enum "eq";
                  enum "neq";
                  enum "lt";
                  enum "lte";
                  enum "gt";
                  enum "gte";
                }
              }
              leaf event-id {
                tailf:cli-drop-node-name;
                tailf:cli-no-value-on-delete;
                type uint32;
              }
            }
            container router {
              tailf:info
                "Specify router context string to match";
              tailf:cli-compact-syntax;
              tailf:cli-sequence-commands;
              tailf:cli-embed-no-on-delete;
              leaf rule {
                tailf:cli-drop-node-name;
                tailf:cli-no-value-on-delete;
                type enumeration {
                  enum "eq";
                  enum "neq";
                }
              }
              leaf router-instance {
                tailf:cli-drop-node-name;
                tailf:cli-no-value-on-delete;
                type string;
              }
              leaf regexp {
                tailf:cli-no-name-on-delete;
                type empty;
              }
            }
            container severity {
              tailf:info
                "Specify severity level to match";
              tailf:cli-compact-syntax;
              tailf:cli-sequence-commands;
              tailf:cli-embed-no-on-delete;
              leaf rule {
                tailf:cli-drop-node-name;
                tailf:cli-no-value-on-delete;
                type enumeration {
                  enum "eq";
                  enum "neq";
                  enum "lt";
                  enum "lte";
                  enum "gt";
                  enum "*";
                }
              }
              leaf severity-level {
                tailf:cli-drop-node-name;
                tailf:cli-no-value-on-delete;
                type enumeration {
                  enum "cleared";
                  enum "indeterminate";
                  enum "critical";
                  enum "major";
                  enum "minor";
                  enum "warning";
                }
              }
            }
            container subject {
              tailf:info
                "Specify subject string to match";
              tailf:cli-compact-syntax;
              tailf:cli-sequence-commands;
              tailf:cli-embed-no-on-delete;
              leaf rule {
                tailf:cli-drop-node-name;
                tailf:cli-no-value-on-delete;
                type enumeration {
                  enum "eq";
                  enum "neq";
                }
              }
              leaf subject {
                tailf:cli-drop-node-name;
                tailf:cli-no-value-on-delete;
                type string;
              }
              leaf regexp {
                tailf:cli-no-name-on-delete;
                type empty;
              }
            }
          }
        }
      }
      list snmp-trap-group {
        key "id";
        leaf id {
          type uint16;
        }
        leaf-list trap-target {
          tailf:cli-flat-list-syntax;
          tailf:cli-no-value-on-delete;
          type string;
        }
        leaf description {
          tailf:cli-embed-no-on-delete;
          tailf:cli-no-value-on-delete;
          type string;
        }
      }
      list log-id {
        key "id";
        leaf id {
          type uint16;
        }
        leaf description {
          tailf:cli-no-value-on-delete;
          type string;
        }
        leaf filter {
          tailf:cli-no-value-on-delete;
          tailf:non-strict-leafref {
            path "../../filter/filter-id";
          }
          type uint16;
        }
        leaf-list from {
          tailf:cli-flat-list-syntax;
          tailf:cli-no-value-on-delete;
          type string;
        }
        leaf time-format {
          tailf:cli-no-value-on-delete;
          type string;
        }
        container to {
          choice choice {
            case file {
              leaf file {
                type uint32;
              }
            }
            case syslog {
              leaf syslog {
                tailf:non-strict-leafref {
                  path "/ncs:devices/ncs:device/ncs:config/alu:log/syslog/id" {
                    tailf:xpath-root 3;
                  }
                }
                type uint32;
              }
            }
            case console {
              leaf console {
                type empty;
              }
            }
            case snmp {
              container snmp {
                presence "true";
                leaf size {
                  tailf:cli-drop-node-name;
                  type uint32;
                }
              }
            }
            case memory {
              leaf memory {
                type empty;
              }
            }
            case session {
              leaf session {
                type uint32;
              }
            }
          }
        }
        leaf shutdown {
          tailf:cli-boolean-no;
          default "false";
          type boolean;
        }
      }
      list syslog {
        key "id";
        leaf id {
          type uint32;
        }
        leaf address {
          tailf:cli-no-value-on-delete;
          type union {
            type inet:ipv4-address;
            type inet:ipv6-address;
          }
        }
        leaf description {
          tailf:cli-no-value-on-delete;
          type string;
        }
        leaf facility {
          tailf:cli-no-value-on-delete;
          type string;
        }
        leaf log-prefix {
          tailf:cli-no-value-on-delete;
          type string;
        }
        leaf level {
          type enumeration {
            enum "emergency";
            enum "alert";
            enum "critical";
            enum "error";
            enum "warning";
            enum "notice";
            enum "info";
            enum "debug";
          }
        }
      }
    }
    container service {
      tailf:ncs-device-type "cli-ned";
      tailf:display-when "not(../../ncs:module) or ../../ncs:module[ncs:name='tailf-ned-alu-sr']";
      tailf:info
        "Services configuration";
      tailf:cli-diff-dependency "/alu:port/shutdown" {
        tailf:xpath-root 3;
        tailf:cli-trigger-on-all;
      }
      tailf:cli-add-mode;
      list customer {
        tailf:info
          "Provision a customer";
        tailf:cli-recursive-delete;
        tailf:cli-embed-no-on-delete;
        key "customer-id";
        leaf customer-id {
          type uint32 {
            tailf:info
              "<customer-id>;;[1..2147483647]";
            range "1 .. 2147483647";
          }
        }
        leaf contact {
          tailf:cli-embed-no-on-delete;
          tailf:cli-no-value-on-delete;
          type string;
        }
        leaf description {
          tailf:cli-embed-no-on-delete;
          tailf:cli-no-value-on-delete;
          type string;
        }
        list multi-service-site {
          tailf:cli-embed-no-on-delete;
          tailf:cli-diff-dependency "/alu:lag" {
            tailf:xpath-root 3;
          }
          tailf:cli-diff-dependency "/alu:port" {
            tailf:xpath-root 3;
          }
          key "customer-site-name";
          leaf customer-site-name {
            type string;
          }
          container assignment {
            tailf:cli-embed-no-on-delete;
            choice choice {
              leaf port {
                tailf:cli-no-name-on-delete;
                tailf:cli-no-value-on-delete;
                tailf:non-strict-leafref {
                  path "/ncs:devices/ncs:device/ncs:config/alu:port/port-id" {
                    tailf:xpath-root 3;
                  }
                }
                type string;
              }
              leaf card {
                tailf:cli-no-name-on-delete;
                tailf:cli-no-value-on-delete;
                tailf:non-strict-leafref {
                  path "/ncs:devices/ncs:device/ncs:config/alu:card/slot-number" {
                    tailf:xpath-root 3;
                  }
                }
                type string;
              }
            }
          }
          leaf description {
            tailf:cli-embed-no-on-delete;
            tailf:cli-no-value-on-delete;
            type string;
          }
          container egress {
            tailf:cli-add-mode;
            container agg-rate-limit {
              presence "present";
              tailf:cli-sequence-commands;
              tailf:cli-compact-syntax;
              tailf:cli-full-no;
              tailf:cli-recursive-delete;
              tailf:cli-embed-no-on-delete;
              leaf agg-rate {
                tailf:cli-drop-node-name;
                tailf:cli-delete-container-on-delete;
                mandatory true;
                type string;
              }
              leaf queue-frame-based-accounting {
                tailf:cli-hide-in-submode;
                type empty;
              }
            }
            leaf policer-control-policy {
              type string;
            }
            leaf scheduler-policy {
              tailf:cli-no-value-on-delete;
              tailf:non-strict-leafref {
                path "/ncs:devices/ncs:device/ncs:config/alu:qos/scheduler-policy/scheduler-policy-name" {
                  tailf:xpath-root 3;
                }
              }
              type string;
            }
            container scheduler-override {
              tailf:cli-add-mode;
              list scheduler {
                tailf:cli-recursive-delete;
                tailf:cli-embed-no-on-delete;
                key "scheduler-name";
                leaf scheduler-name {
                  type string;
                }
                container rate {
                  tailf:cli-sequence-commands;
                  tailf:cli-compact-syntax;
                  tailf:cli-embed-no-on-delete;
                  leaf pir-rate {
                    tailf:cli-drop-node-name;
                    tailf:cli-no-value-on-delete;
                    type string;
                  }
                  leaf cir {
                    tailf:cli-no-name-on-delete;
                    tailf:cli-no-value-on-delete;
                    type string;
                  }
                }
              }
            }
          }
          container ingress {
            tailf:cli-add-mode;
            leaf policer-control-policy {
              type string;
            }
            leaf scheduler-policy {
              tailf:cli-no-value-on-delete;
              tailf:non-strict-leafref {
                path "/ncs:devices/ncs:device/ncs:config/alu:qos/scheduler-policy/scheduler-policy-name" {
                  tailf:xpath-root 3;
                }
              }
              type string;
            }
            container scheduler-override {
              tailf:cli-add-mode;
              list scheduler {
                tailf:cli-recursive-delete;
                tailf:cli-embed-no-on-delete;
                key "scheduler-name";
                leaf scheduler-name {
                  type string;
                }
                container rate {
                  presence "present";
                  tailf:cli-sequence-commands;
                  tailf:cli-compact-syntax;
                  tailf:cli-embed-no-on-delete;
                  leaf pir-rate {
                    tailf:cli-drop-node-name;
                    tailf:cli-no-value-on-delete;
                    mandatory true;
                    type string;
                  }
                  leaf cir {
                    tailf:cli-no-name-on-delete;
                    tailf:cli-no-value-on-delete;
                    type string;
                  }
                }
              }
            }
          }
          leaf tod-suite {
            type string;
          }
        }
        leaf phone {
          type string;
        }
      }
      list sdp {
        tailf:info
          "Provision a SDP";
        tailf:cli-embed-no-on-delete;
        key "sdp-id";
        leaf sdp-id {
          type uint32 {
            range "1 .. 17407";
            tailf:info
              "<sdp-id>;;[1..17407]";
          }
        }
        leaf accounting-policy {
          tailf:info
            "Configure accounting-policy to be used";
          tailf:cli-no-value-on-delete;
          type uint8 {
            range "1..99";
          }
        }
        leaf adv-mtu-override {
          tailf:info
            "Override the advertised VC MTU";
          tailf:cli-no-value-on-delete;
          type empty;
        }
        leaf bgp-tunnel {
          tailf:info
            "Enable/disable BGP tunnels";
          type empty;
        }
        container binding {
          tailf:info
            "Configure binding information";
          tailf:cli-add-mode;
          leaf port {
            tailf:info
              "port;; <port-id | lag-id>";
            tailf:cli-no-value-on-delete;
            type string;
          }
          list pw-port {
            tailf:info
              "Configure pseudo-wire port information";
            tailf:cli-embed-no-on-delete;
            key "pw-port-id";
            leaf pw-port-id {
              tailf:info
                "<pw-port-id>;;<1..10239>";
              type uint32 {
                range "1..10239";
              }
            }
            leaf vc-id {
              tailf:info
                "<vc-id>;;<1..4294967295>";
              tailf:cli-hide-in-submode;
              type uint32 {
                range "1..4294967295";
              }
            }
            container egress {
              tailf:info
                "Configure pseudo-wire port egress side parameters";
              container shaping {
                tailf:cli-embed-no-on-delete;
                choice choice {
                  leaf vport {
                    tailf:info
                      "<vport-name>";
                    tailf:cli-no-value-on-delete;
                    type string;
                  }
                  leaf int-dest-id {
                    tailf:info
                      " <int-dest-id>";
                    tailf:cli-no-value-on-delete;
                    type string;
                  }
                }
              }
            }
            leaf vc-type {
              tailf:info
                "<vc-type>;;<ether|vlan>";
              tailf:cli-no-value-on-delete;
              type enumeration {
                enum "ether";
                enum "vlan";
              }
            }
            leaf vlan-vc-tag {
              tailf:info
                "<vlan-id>;;<0..4094>";
              tailf:cli-no-value-on-delete;
              type uint16 {
                range "0..4094";
              }
            }
            leaf shutdown {
              tailf:info
                "Enable/Disable pseudo-wire port";
              tailf:cli-boolean-no;
              default "true";
              type boolean;
            }
          }
        }
        leaf booking-factor {
          tailf:info
            "Configure the SDP booking-factor";
          tailf:cli-no-value-on-delete;
          type uint16 {
            range "0..1000";
          }
        }
        leaf collect-stats {
          tailf:info
            "Enable/disable statistics collection";
          tailf:cli-no-value-on-delete;
          type empty;
        }
        leaf delivery-type {
          tailf:cli-hide-in-submode;
          tailf:cli-drop-node-name;
          tailf:cli-no-name-on-delete;
          tailf:cli-no-value-on-delete;
          type enumeration {
            enum "gre";
            enum "mpls";
            enum "l2tpv3";
          }
        }
        leaf description {
          tailf:cli-no-value-on-delete;
          type string;
        }
        leaf far-end {
          tailf:cli-no-value-on-delete;
          type union {
            type inet:ipv4-address;
            type inet:ipv6-address;
          }
        }
        container keep-alive {
          tailf:info
            "Configure keep alive parameters";
          tailf:cli-add-mode;
          leaf hello-time {
            tailf:info
              "Configure keep-alive hello time";
            tailf:cli-no-value-on-delete;
            type uint16 {
              range "1..3600";
            }
          }
          leaf hold-down-time {
            tailf:info
              "Configure keep-alive hold down time";
            tailf:cli-no-value-on-delete;
            type uint16 {
              range "1..3600";
            }
          }
          leaf max-drop-count {
            tailf:info
              "Configure keep-alive max-drop-count";
            tailf:cli-no-value-on-delete;
            type uint8 {
              range "1..5";
            }
          }
          leaf message-length {
            tailf:info
              "Configure keep-alive message-length";
            tailf:cli-no-value-on-delete;
            type uint16 {
              range "40..9198";
            }
          }
          leaf timeout {
            tailf:info
              "Configure keep-alive hello timeout";
            tailf:cli-no-value-on-delete;
            type uint8 {
              range "1..10";
            }
          }
          leaf shutdown {
            tailf:info
              "Enable/disable keep-alive";
            tailf:cli-boolean-no;
            default "true";
            type boolean;
          }
        }
        leaf ldp {
          tailf:info
            "Enable/disable LDP-signaled LSP's";
          type empty;
        }
        leaf lsp {
          tailf:info
            "Configure LSP to be used by SDP";
          tailf:cli-no-value-on-delete;
          tailf:cli-diff-dependency "/alu:router/mpls/lsp" {
            tailf:xpath-root 3;
          }
          tailf:cli-diff-dependency "/alu:router/mpls/static-lsp" {
            tailf:xpath-root 3;
          }
          tailf:non-strict-leafref {
            path "/ncs:devices/ncs:device/ncs:config/alu:router/mpls/lsp/name" {
              tailf:xpath-root 3;
            }
          }
          type string;
        }
        container class-forwarding {
          tailf:info
            "Configure class-based forwarding";
          tailf:cli-embed-no-on-delete;
          tailf:cli-add-mode;
          leaf default-lsp {
            tailf:info
              "<default-lsp;;<lsp-name>";
            tailf:cli-hide-in-submode;
            tailf:cli-no-name-on-delete;
            tailf:cli-no-value-on-delete;
            type string;
          }
          leaf enforce-diffserv-lsp-fc {
            tailf:info
              "Configure validation of support of fc by lsp with RSVP";
            type empty;
          }
          leaf fc {
            tailf:info
              "Configure a forwarding class to LSP mapping";
            tailf:cli-no-value-on-delete;
            type enumeration {
              enum "be";
              enum "l2";
              enum "af";
              enum "l1";
              enum "h2";
              enum "ef";
              enum "h1";
              enum "nc";
            }
          }
          leaf multicast-lsp {
            tailf:info
              "Configure an LSP for all MC traffic";
            tailf:cli-no-value-on-delete;
            type string;
          }
          leaf shutdown {
            tailf:info
              "Administratively enable/disable class-based forwarding";
            tailf:cli-boolean-no;
            default "true";
            type boolean;
          }
        }
        leaf metric {
          tailf:info
            "Configure SDP Metric";
          tailf:cli-no-value-on-delete;
          type uint16 {
            range "1..65535";
          }
        }
        container mixed-lsp-mode {
          tailf:info
            "Enable/disable Mixed LSP mode";
          tailf:cli-embed-no-on-delete;
          tailf:cli-add-mode;
          leaf revert-time {
            tailf:info
              "Configure the time to wait before reverting";
            tailf:cli-no-value-on-delete;
            type union {
              type uint16 {
                range "0..600";
              }
              type enumeration {
                enum "infinite";
              }
            }
          }
        }
        leaf network-domain {
          tailf:info
            "Configure network-domain";
          tailf:cli-no-value-on-delete;
          type string;
        }
        leaf path-mtu {
          tailf:info
            "Configure path MTU";
          tailf:cli-no-value-on-delete;
          type uint16 {
            range "576..9194";
          }
        }
        leaf pbb-etype {
          tailf:info
            "Configure PBB ethertype";
          tailf:cli-no-value-on-delete;
          type uint16 {
            range "1536..65535";
          }
        }
        leaf signaling {
          tailf:info
            "Configure type of VC label signaling";
          tailf:cli-no-value-on-delete;
          type enumeration {
            enum "off";
            enum "tldp";
            enum "bgp";
          }
        }
        leaf local-end {
          tailf:cli-no-value-on-delete;
          type inet:ipv6-address;
        }
        leaf tunnel-far-end {
          tailf:info
            "Configure tunnel-far-end address";
          tailf:cli-no-value-on-delete;
          type inet:ipv4-address;
        }
        leaf vlan-vc-etype {
          tailf:info
            "Configure VLAN VC ethertype";
          tailf:cli-no-value-on-delete;
          type uint32;
        }
        leaf shutdown {
          tailf:info
            "Administratively enable/disable the SDP";
          tailf:cli-boolean-no;
          default "true";
          type boolean;
        }
      }
      list epipe {
        tailf:info
          "Provision an Ether-Pipe Service";
        tailf:cli-recursive-delete;
        tailf:cli-embed-no-on-delete;
        tailf:cli-diff-dependency "/alu:port" {
          tailf:xpath-root 3;
        }
        tailf:cli-diff-dependency "/alu:lag" {
          tailf:xpath-root 3;
        }
        key "service-id";
        leaf service-id {
          type uint32 {
            range "1 .. 2147483650";
            tailf:info
              "<service-id>;;[1..2147483650]";
          }
        }
        leaf customer {
          tailf:cli-hide-in-submode;
          tailf:cli-no-name-on-delete;
          tailf:cli-no-value-on-delete;
          type leafref {
            path "/ncs:devices/ncs:device/ncs:config/alu:service/customer/customer-id" {
              tailf:xpath-root 3;
            }
          }
        }
        leaf description {
          tailf:cli-embed-no-on-delete;
          tailf:cli-no-value-on-delete;
          type string;
        }
        leaf vc-switching {
          tailf:cli-hide-in-submode;
          tailf:cli-no-name-on-delete;
          type empty;
        }
        list sap {
          tailf:info
            "Provision a SAP";
          tailf:cli-embed-no-on-delete;
          tailf:cli-diff-dependency "/alu:service/epipe/endpoint" {
            tailf:xpath-root 3;
          }
          tailf:cli-diff-dependency "/alu:port" {
            tailf:xpath-root 3;
          }
          key "sap-id";
          leaf sap-id {
            tailf:cli-diff-dependency "/alu:service/ies/interface/sap[sap-id=current()/../sap-id]" {
              tailf:xpath-root 3;
              tailf:cli-trigger-on-set;
            }
            tailf:cli-diff-dependency "/alu:service/vpls/sap[sap-id=current()/../sap-id]" {
              tailf:xpath-root 3;
              tailf:cli-trigger-on-set;
            }
            tailf:cli-diff-dependency "/alu:service/vprn/interface/sap[sap-id=current()/../sap-id]" {
              tailf:xpath-root 3;
              tailf:cli-trigger-on-set;
            }
            tailf:cli-diff-dependency "/alu:service/epipe/sap[sap-id=current()/../sap-id]" {
              tailf:xpath-root 3;
              tailf:cli-trigger-on-set;
            }
            tailf:info
              "<sap-id>;;different formats depending on port mode";
            type string;
          }
          leaf endpoint {
            tailf:cli-hide-in-submode;
            tailf:cli-no-name-on-delete;
            tailf:cli-no-value-on-delete;
            type leafref {
              path "/ncs:devices/ncs:device/ncs:config/alu:service/epipe/endpoint/endpoint-name" {
                tailf:xpath-root 3;
              }
            }
          }
          container egress {
            tailf:cli-add-mode;
            leaf qos {
              tailf:info
                "Apply egress qos policy";
              type uint16;
              tailf:non-strict-leafref {
                path "/ncs:devices/ncs:device/ncs:config/alu:qos/sap-egress/policy-id" {
                  tailf:xpath-root 3;
                }
              }
            }
          }
          container ingress {
            tailf:cli-add-mode;
            leaf qos {
              tailf:info
                "Apply ingress qos policy";
              type uint16;
              tailf:non-strict-leafref {
                path "/ncs:devices/ncs:device/ncs:config/alu:qos/sap-ingress/policy-id" {
                  tailf:xpath-root 3;
                }
              }
            }
          }
          leaf description {
            tailf:info
              "Description for the SAP";
            tailf:cli-embed-no-on-delete;
            tailf:cli-no-value-on-delete;
            type string;
          }
          container eth-cfm {
            tailf:cli-add-mode;
            uses eth-cfm;
          }
          leaf multi-service-site {
            tailf:cli-no-value-on-delete;
            type leafref {
              path "/ncs:devices/ncs:device/ncs:config/alu:service/customer/multi-service-site/customer-site-name" {
                tailf:xpath-root 3;
              }
            }
          }
          leaf oper-group {
            tailf:info
              "Configure operational-group";
            tailf:cli-embed-no-on-delete;
            tailf:cli-no-value-on-delete;
            tailf:non-strict-leafref {
              path "/ncs:devices/ncs:device/ncs:config/alu:service/oper-group/group-name" {
                tailf:xpath-root 3;
              }
            }
            type string;
          }
          leaf shutdown {
            type empty;
          }
        }
        leaf service-name {
          tailf:info
            "Configure a service name";
          tailf:cli-embed-no-on-delete;
          tailf:cli-no-value-on-delete;
          type string;
        }
        leaf service-mtu {
          tailf:info
            "Configure service MTU";
          tailf:cli-embed-no-on-delete;
          tailf:cli-no-value-on-delete;
          type uint16 {
            range "1..9194";
          }
        }
        list site {
          tailf:cli-embed-no-on-delete;
          tailf:cli-recursive-delete;
          key "name";
          leaf name {
            type string {
              length "1..32";
            }
          }
          leaf boot-timer {
            tailf:info
              "Configure/Override site boot-timer";
            tailf:cli-embed-no-on-delete;
            tailf:cli-no-value-on-delete;
            type uint16 {
              range "0..600";
            }
          }
          leaf sap {
            tailf:info
              "tailf:cli-embed-no-on-delete";
            tailf:cli-no-value-on-delete;
            type string;
          }
          leaf site-activation-timer {
            tailf:info
              "Configure/Override site activation timer";
            tailf:cli-embed-no-on-delete;
            tailf:cli-no-value-on-delete;
            type uint16 {
              range "0..100";
            }
          }
          leaf site-id {
            tailf:info
              "Configure site identifier";
            tailf:cli-embed-no-on-delete;
            tailf:cli-no-value-on-delete;
            type uint16;
          }
          leaf shutdown {
            tailf:info
              "Administratively enable/disable the site";
            tailf:cli-boolean-no;
            default "true";
            type boolean;
          }
        }
        list spoke-sdp {
          tailf:info
            "<sdp-id>:<vc-id>";
          tailf:cli-embed-no-on-delete;
          tailf:cli-key-format "$(1):$(2)";
          uses sdp-common;
          key "sdp-id vc-id";
          container egress {
            tailf:cli-add-mode;
            tailf:cli-no-name-on-delete;
            container l2tpv3 {
              tailf:cli-add-mode;
              tailf:cli-no-name-on-delete;
              leaf cookie {
                tailf:cli-no-name-on-delete;
                tailf:cli-no-value-on-delete;
                type string;
              }
            }
          }
          container ingress {
            tailf:cli-add-mode;
            tailf:cli-no-name-on-delete;
            container l2tpv3 {
              tailf:cli-add-mode;
              tailf:cli-no-name-on-delete;
              leaf cookie {
                tailf:cli-no-name-on-delete;
                tailf:cli-no-value-on-delete;
                type string;
              }
            }
          }
          leaf pw-status-signaling {
            type empty;
          }
          leaf control-word {
            tailf:info
              "Enable/disable setting the CW bit in the label message";
            tailf:cli-embed-no-on-delete;
            type empty;
          }
          leaf precedence {
            tailf:info
              "Configure the spoke-sdp precedence";
            tailf:cli-embed-no-on-delete;
            tailf:cli-no-value-on-delete;
            type union {
              type enumeration {
                enum "primary";
              }
              type uint8 {
                range "1..4";
              }
            }
          }
        }
        list endpoint {
          tailf:info
            "Configure a service end-point";
          tailf:cli-embed-no-on-delete;
          key "endpoint-name";
          leaf endpoint-name {
            type string;
          }
          leaf active-hold-delay {
            tailf:info
              "Configure the time to hold the active status";
            tailf:cli-embed-no-on-delete;
            tailf:cli-no-value-on-delete;
            type uint8 {
              range "1..60";
            }
          }
          leaf description {
            tailf:info
              "Description for the service end-point";
            tailf:cli-embed-no-on-delete;
            tailf:cli-no-value-on-delete;
            type string;
          }
          leaf revert-time {
            tailf:info
              "Configure the time to wait before reverting to primary";
            tailf:cli-embed-no-on-delete;
            tailf:cli-no-value-on-delete;
            type union {
              type enumeration {
                enum "infinite";
              }
              type uint16 {
                range "0..600";
              }
            }
          }
          leaf standby-signaling-master {
            tailf:info
              "Enable PW standby-signaling master";
            tailf:cli-no-value-on-delete;
            type empty;
          }
          leaf standby-signaling-slave {
            tailf:info
              "Enable PW standby-signaling master";
            tailf:cli-no-value-on-delete;
            type empty;
          }
        }
        leaf shutdown {
          tailf:cli-boolean-no;
          default "true";
          type boolean;
        }
      }
      list oper-group {
        tailf:info
          "Configure a Operational-Group information";
        key "group-name";
        leaf group-name {
          tailf:cli-embed-no-on-delete;
          type string;
        }
        container hold-time {
          tailf:info
            "Configure hold-time information";
          tailf:cli-add-mode;
          leaf group {
            tailf:info
              "Configure group up/down time information";
            tailf:cli-embed-no-on-delete;
            type empty;
          }
        }
      }
      list ies {
        tailf:info
          "Provision an Internet Enhanced Service";
        tailf:cli-recursive-delete;
        tailf:cli-embed-no-on-delete;
        tailf:cli-diff-dependency "/alu:port" {
          tailf:xpath-root 3;
        }
        tailf:cli-diff-dependency "/alu:lag" {
          tailf:xpath-root 3;
        }
        key "service-id";
        leaf service-id {
          type uint32 {
            range "1 .. 2147483650";
            tailf:info
              "<service-id>;;[1..2147483650]";
          }
        }
        leaf customer {
          tailf:cli-hide-in-submode;
          tailf:cli-no-name-on-delete;
          tailf:cli-no-value-on-delete;
          type leafref {
            path "/ncs:devices/ncs:device/ncs:config/alu:service/customer/customer-id" {
              tailf:xpath-root 3;
            }
          }
        }
        leaf description {
          tailf:cli-embed-no-on-delete;
          tailf:cli-no-value-on-delete;
          type string;
        }
        list subscriber-interface {
          tailf:cli-recursive-delete;
          tailf:cli-embed-no-on-delete;
          key "id";
          leaf id {
            type string;
          }
          leaf address {
            type tailf:ipv4-address-and-prefix-length;
          }
          list group-interface {
            tailf:cli-recursive-delete;
            tailf:cli-embed-no-on-delete;
            key "id";
            leaf id {
              type string;
            }
            leaf description {
              tailf:cli-no-value-on-delete;
              type string;
            }
            container icmp {
              tailf:cli-add-mode;
              leaf mask-reply {
                type boolean;
                tailf:cli-boolean-no;
              }
              container redirects {
                tailf:cli-compact-syntax;
                tailf:cli-sequence-commands {
                  tailf:cli-reset-siblings;
                }
                leaf number {
                  tailf:cli-drop-node-name;
                  tailf:cli-no-value-on-delete;
                  type uint16 {
                    range "10..1000";
                  }
                }
                leaf seconds {
                  tailf:cli-drop-node-name;
                  tailf:cli-no-value-on-delete;
                  type uint8 {
                    range "1..60";
                  }
                }
              }
              container unreachables {
                tailf:cli-compact-syntax;
                tailf:cli-sequence-commands {
                  tailf:cli-reset-siblings;
                }
                leaf number {
                  tailf:cli-drop-node-name;
                  tailf:cli-no-value-on-delete;
                  type uint16 {
                    range "10..1000";
                  }
                }
                leaf seconds {
                  tailf:cli-drop-node-name;
                  tailf:cli-no-value-on-delete;
                  type uint8 {
                    range "1..60";
                  }
                }
              }
              container ttl-expired {
                tailf:cli-compact-syntax;
                tailf:cli-sequence-commands {
                  tailf:cli-reset-siblings;
                }
                leaf number {
                  tailf:cli-drop-node-name;
                  tailf:cli-no-value-on-delete;
                  type uint16 {
                    range "10..1000";
                  }
                }
                leaf seconds {
                  tailf:cli-drop-node-name;
                  tailf:cli-no-value-on-delete;
                  type uint8 {
                    range "1..60";
                  }
                }
              }
            }
            container ipv6 {
              tailf:cli-add-mode;
              container router-advertisements {
                tailf:cli-add-mode;
                leaf managed-configuration {
                  type empty;
                }
                leaf shutdown {
                  tailf:cli-boolean-no;
                  default "true";
                  type boolean;
                }
              }
              container dhcp6 {
                tailf:cli-add-mode;
                container proxy-server {
                  tailf:cli-add-mode;
                  container lease-time {
                    tailf:cli-compact-syntax;
                    leaf days {
                      tailf:cli-no-name-on-delete;
                      tailf:cli-no-value-on-delete;
                      type uint16;
                    }
                    leaf hrs {
                      tailf:cli-no-name-on-delete;
                      tailf:cli-no-value-on-delete;
                      type uint16;
                    }
                    leaf min {
                      tailf:cli-no-name-on-delete;
                      tailf:cli-no-value-on-delete;
                      type uint16;
                    }
                    leaf sec {
                      tailf:cli-no-name-on-delete;
                      tailf:cli-no-value-on-delete;
                      type uint16;
                    }
                  }
                  leaf shutdown {
                    tailf:cli-boolean-no;
                    default "true";
                    type boolean;
                  }
                }
              }
            }
            leaf arp-populate {
              type empty;
            }
            container dhcp {
              tailf:cli-add-mode;
              container proxy-server {
                tailf:cli-add-mode;
                container lease-time {
                  tailf:cli-compact-syntax;
                  leaf days {
                    tailf:cli-no-name-on-delete;
                    tailf:cli-no-value-on-delete;
                    type uint16;
                  }
                  leaf hrs {
                    tailf:cli-no-name-on-delete;
                    tailf:cli-no-value-on-delete;
                    type uint16;
                  }
                  leaf min {
                    tailf:cli-no-name-on-delete;
                    tailf:cli-no-value-on-delete;
                    type uint16;
                  }
                  leaf sec {
                    tailf:cli-no-name-on-delete;
                    tailf:cli-no-value-on-delete;
                    type uint16;
                  }
                }
                leaf shutdown {
                  tailf:cli-boolean-no;
                  default "true";
                  type boolean;
                }
              }
              container option {
                tailf:cli-add-mode;
                leaf action {
                  tailf:cli-no-value-on-delete;
                  type enumeration {
                    enum "replace";
                    enum "drop";
                    enum "keep";
                  }
                }
                container circuit-id {
                  presence "true";
                  leaf id {
                    tailf:cli-drop-node-name;
                    tailf:cli-no-value-on-delete;
                    type enumeration {
                      enum "ascii-tuple";
                      enum "ifindex";
                      enum "sap-id";
                      enum "vlan-ascii-tuple";
                    }
                  }
                }
                container remote-id {
                  presence "true";
                  choice remote-id {
                    leaf mac {
                      tailf:cli-drop-node-name;
                      type string;
                      tailf:cli-disallow-value "string";
                    }
                    leaf string {
                      type string;
                    }
                  }
                }
              }
              leaf-list server {
                type inet:ipv4-address;
                tailf:cli-flat-list-syntax;
                tailf:cli-no-value-on-delete;
              }
              leaf trusted {
                type empty;
              }
              container lease-populate {
                presence "true";
                tailf:cli-compact-syntax;
                tailf:cli-sequence-commands {
                  tailf:cli-reset-siblings;
                }
                leaf nr-of-leases {
                  tailf:cli-drop-node-name;
                  tailf:cli-no-value-on-delete;
                  type uint16;
                }
                leaf l2-header {
                  tailf:cli-no-name-on-delete;
                  type empty;
                }
                leaf mac {
                  tailf:cli-no-name-on-delete;
                  tailf:cli-no-value-on-delete;
                  type string;
                }
              }
              container gi-address {
                tailf:cli-compact-syntax;
                tailf:cli-sequence-commands {
                  tailf:cli-reset-siblings;
                }
                leaf address {
                  tailf:cli-drop-node-name;
                  type inet:ipv4-address;
                }
                leaf src-ip-address {
                  type empty;
                }
              }
              leaf shutdown {
                tailf:cli-boolean-no;
                default "true";
                type boolean;
              }
            }
            list sap {
              tailf:cli-recursive-delete;
              tailf:cli-embed-no-on-delete;
              key "id";
              leaf id {
                type string;
              }
              leaf description {
                tailf:cli-embed-no-on-delete;
                tailf:cli-no-value-on-delete;
                type string;
              }
              leaf anti-spoof {
                tailf:cli-no-value-on-delete;
                type enumeration {
                  enum "ip";
                  enum "ip-mac";
                  enum "nh-mac";
                }
              }
              container sub-sla-mgmt {
                tailf:cli-add-mode;
                tailf:cli-recursive-delete;
                container def-sub-id {
                  choice sub-id-choice {
                    leaf string {
                      tailf:cli-no-value-on-delete;
                      tailf:cli-no-name-on-delete;
                      type string;
                    }
                    leaf use-auto-id {
                      tailf:cli-no-name-on-delete;
                      type empty;
                    }
                    leaf use-sap-id {
                      tailf:cli-no-name-on-delete;
                      type empty;
                    }
                  }
                }
                leaf def-sub-profile {
                  tailf:cli-no-value-on-delete;
                  type string;
                }
                leaf def-sla-profile {
                  tailf:cli-no-value-on-delete;
                  type string;
                }
                container single-sub-parameters {
                  tailf:cli-add-mode;
                  tailf:cli-no-name-on-delete;
                  leaf profiled-traffic-only {
                    type empty;
                  }
                }
                leaf shutdown {
                  tailf:cli-boolean-no;
                  default "true";
                  type boolean;
                }
              }
              leaf calling-station-id {
                tailf:cli-no-value-on-delete;
                type string;
              }
              leaf shutdown {
                tailf:cli-boolean-no;
                default "true";
                type boolean;
              }
            }
          }
        }
        list interface {
          tailf:cli-recursive-delete;
          tailf:cli-embed-no-on-delete;
          tailf:cli-diff-dependency "/alu:port" {
            tailf:xpath-root 3;
          }
          tailf:cli-diff-dependency "/alu:lag" {
            tailf:xpath-root 3;
          }
          key "ip-int-name";
          leaf ip-int-name {
            type string;
          }
          leaf address {
            tailf:info
              "Assigns an IP address to the interface";
            tailf:cli-no-value-on-delete;
            type tailf:ipv4-address-and-prefix-length;
          }
          leaf allow-directed-broadcasts {
            tailf:info
              "Enable/disable forwarding of directed broadcasts";
            type empty;
          }
          leaf arp-populate {
            tailf:info
              "Configures the ARP populate option";
            type empty;
          }
          leaf arp-timeout {
            tailf:info
              "Configures timeout for an ARP entry learned";
            tailf:cli-no-value-on-delete;
            type uint16;
          }
          leaf authentication-policy {
            tailf:info
              "Configures the authentication policy for this interface";
            tailf:cli-no-value-on-delete;
            type string;
          }
          container bfd {
            tailf:info
              "Configure BFD parameters";
            tailf:cli-embed-no-on-delete;
            tailf:cli-compact-syntax;
            tailf:cli-sequence-commands;
            leaf transmit-interval {
              tailf:cli-drop-node-name;
              tailf:cli-no-value-on-delete;
              type uint32 {
                range "10..100000";
              }
            }
            leaf receive {
              tailf:cli-no-value-on-delete;
              type uint32 {
                range "10..100000";
              }
            }
            leaf multiplier {
              tailf:cli-no-value-on-delete;
              type uint8 {
                range "3..20";
              }
            }
            leaf echo-receive {
              tailf:cli-no-value-on-delete;
              type uint32 {
                range "100..100000";
              }
            }
            leaf type {
              tailf:cli-no-value-on-delete;
              type enumeration {
                enum "cpm-np";
              }
            }
          }
          container cflowd {
            tailf:info
              "Configure Cflowd collection and analysis on this if";
            tailf:cli-embed-no-on-delete;
            tailf:cli-compact-syntax;
            tailf:cli-sequence-commands;
            leaf id {
              tailf:cli-drop-node-name;
              tailf:cli-no-value-on-delete;
              type enumeration {
                enum "acl";
                enum "interface";
              }
            }
            leaf direction {
              tailf:cli-drop-node-name;
              tailf:cli-no-value-on-delete;
              type enumeration {
                enum "ingress-only";
                enum "egress-only";
                enum "both";
              }
            }
          }
          leaf cpu-protection {
            tailf:info
              "Configure a CPU protection policy";
            tailf:cli-no-value-on-delete;
            type uint8 {
              range "1..255";
            }
          }
          leaf delayed-enable {
            tailf:info
              "Delays making interface operational";
            tailf:cli-no-value-on-delete;
            type uint16 {
              range "1..1200";
            }
          }
          leaf description {
            tailf:info
              "Description for IES interface";
            tailf:cli-no-value-on-delete;
            type string;
          }
          container dhcp {
            tailf:info
              "Configure DHCP parameters";
            tailf:cli-add-mode;
          }
          leaf dynamic-tunnel-redundant-next-hop {
            tailf:info
              "Configure dynamic ISA tunnel redundant next-hop address";
            tailf:cli-no-value-on-delete;
            type inet:ipv4-address;
          }
          leaf enable-ingress-stats {
            tailf:info
              "Enable/disable the gathering of ingress if stats";
            type empty;
          }
          leaf enable-mac-accounting {
            tailf:info
              "Configure MAC Accounting functionality for the if";
            type empty;
          }
          container host-connectivity {
            tailf:info
              "Enable/disable host connectivity verification";
            tailf:cli-embed-no-on-delete;
            tailf:cli-compact-syntax;
            tailf:cli-sequence-commands;
            leaf source {
              tailf:cli-no-value-on-delete;
              type enumeration {
                enum "vrrp";
                enum "interface";
              }
            }
            leaf interval {
              tailf:cli-no-value-on-delete;
              type uint16 {
                range "1..6000";
              }
            }
            leaf action {
              tailf:cli-no-value-on-delete;
              type enumeration {
                enum "remove";
                enum "alarm";
              }
            }
            leaf timeout {
              tailf:cli-no-value-on-delete;
              type uint8 {
                range "10..60";
              }
            }
            leaf count {
              tailf:cli-no-value-on-delete;
              type uint8 {
                range "2..29";
              }
            }
          }
          container icmp {
            tailf:info
              "Configure ICMP parameters for the interface";
            tailf:cli-add-mode;
            leaf mask-reply {
              tailf:info
                "Enable/disable responses to ICMP mask requests";
              type empty;
            }
            container redirects {
              tailf:info
                "Configures rate for ICMP redirect messages";
              tailf:cli-embed-no-on-delete;
              tailf:cli-compact-syntax;
              tailf:cli-sequence-commands;
              leaf number {
                tailf:cli-drop-node-name;
                tailf:cli-no-value-on-delete;
                type uint16 {
                  range "10..1000";
                }
              }
              leaf seconds {
                tailf:cli-drop-node-name;
                tailf:cli-no-value-on-delete;
                type uint8 {
                  range "1..60";
                }
              }
            }
            container ttl-expired {
              tailf:info
                "Configures rate for ICMP TTL expired messages";
              tailf:cli-embed-no-on-delete;
              tailf:cli-compact-syntax;
              tailf:cli-sequence-commands;
              leaf number {
                tailf:cli-drop-node-name;
                tailf:cli-no-value-on-delete;
                type uint16 {
                  range "10..1000";
                }
              }
              leaf seconds {
                tailf:cli-drop-node-name;
                tailf:cli-no-value-on-delete;
                type uint8 {
                  range "1..60";
                }
              }
            }
            container unreachables {
              tailf:info
                "Configures rate for ICMP unreachable messages";
              tailf:cli-embed-no-on-delete;
              tailf:cli-compact-syntax;
              tailf:cli-sequence-commands;
              leaf number {
                tailf:cli-drop-node-name;
                tailf:cli-no-value-on-delete;
                type uint16 {
                  range "10..1000";
                }
              }
              leaf seconds {
                tailf:cli-drop-node-name;
                tailf:cli-no-value-on-delete;
                type uint8 {
                  range "1..60";
                }
              }
            }
          }
          leaf ip-mtu {
            tailf:info
              "Configure the interface IP MTU";
            tailf:cli-no-value-on-delete;
            type uint16 {
              range "512..9000";
            }
          }
          container ipv6 {
            tailf:cli-add-mode;
            list address {
              tailf:cli-embed-no-on-delete;
              tailf:cli-suppress-mode;
              key "addr";
              leaf addr {
                type tailf:ipv6-address-and-prefix-length;
              }
            }
            container dhcp6-relay {
              tailf:cli-add-mode;
              tailf:cli-embed-no-on-delete;
              leaf description {
                tailf:cli-embed-no-on-delete;
                tailf:cli-no-value-on-delete;
                type string;
              }
              container lease-populate {
                presence "present";
                tailf:cli-sequence-commands;
                tailf:cli-compact-syntax;
                tailf:cli-no-name-on-delete;
                leaf nbr-of-leases {
                  tailf:cli-drop-node-name;
                  tailf:cli-delete-container-on-delete;
                  type uint32 {
                    range "1 .. 8000";
                  }
                }
                leaf route-populate {
                  tailf:cli-incomplete-command;
                  type empty;
                }
                leaf pd {
                  type empty;
                }
                leaf exclude {
                  tailf:cli-break-sequence-commands;
                  type empty;
                }
                leaf na {
                  type empty;
                }
                leaf ta {
                  type empty;
                }
              }
              leaf neighbor-resolution {
                type empty;
              }
              container option {
                tailf:cli-add-mode;
                container interface-id {
                  tailf:cli-embed-no-on-delete;
                  choice choice {
                    leaf sap-id {
                      tailf:cli-no-name-on-delete;
                      type empty;
                    }
                    leaf ifindex {
                      tailf:cli-no-name-on-delete;
                      type empty;
                    }
                    leaf string {
                      tailf:cli-no-name-on-delete;
                      tailf:cli-no-value-on-delete;
                      type string;
                    }
                  }
                }
                leaf remote-id {
                  type empty;
                }
              }
              leaf source-address {
                tailf:cli-embed-no-on-delete;
                tailf:cli-case-insensitive;
                type inet:ipv6-address;
              }
              leaf link-address {
                tailf:cli-embed-no-on-delete;
                type inet:ipv6-address;
              }
              list server {
                tailf:cli-embed-no-on-delete;
                tailf:cli-suppress-mode;
                max-elements 8;
                key "ipv6z-address";
                leaf ipv6z-address {
                  type inet:ipv6-address;
                }
              }
              leaf shutdown {
                tailf:cli-boolean-no;
                default "true";
                type boolean;
              }
            }
            container urpf-check {
              tailf:cli-add-mode;
              leaf ignore-default {
                tailf:cli-embed-no-on-delete;
                type empty;
              }
              container mode {
                tailf:cli-embed-no-on-delete;
                choice choice {
                  leaf strict {
                    tailf:cli-no-name-on-delete;
                    type empty;
                  }
                  leaf loose {
                    tailf:cli-no-name-on-delete;
                    type empty;
                  }
                  leaf strict-no-ecmp {
                    tailf:cli-no-name-on-delete;
                    type empty;
                  }
                }
              }
            }
          }
          list sap {
            tailf:info
              "Provision a SAP";
            tailf:cli-embed-no-on-delete;
            max-elements 1;
            key "sap-id";
            leaf sap-id {
              tailf:cli-diff-dependency "/alu:service/epipe/sap[sap-id=current()/../sap-id]" {
                tailf:xpath-root 3;
                tailf:cli-trigger-on-set;
              }
              tailf:cli-diff-dependency "/alu:service/vpls/sap[sap-id=current()/../sap-id]" {
                tailf:xpath-root 3;
                tailf:cli-trigger-on-set;
              }
              tailf:cli-diff-dependency "/alu:service/vprn/interface/sap[sap-id=current()/../sap-id]" {
                tailf:xpath-root 3;
                tailf:cli-trigger-on-set;
              }
              tailf:cli-diff-dependency "/alu:service/ies/interface/sap[sap-id=current()/../sap-id]" {
                tailf:xpath-root 3;
                tailf:cli-trigger-on-set;
              }
              tailf:info
                "<sap-id>;;different formats depending on port mode";
              type string;
            }
            leaf description {
              tailf:info
                "Description for the SAP";
              tailf:cli-embed-no-on-delete;
              tailf:cli-no-value-on-delete;
              type string;
            }
            container egress {
              tailf:info
                "Configure egress policies";
              tailf:cli-add-mode;
              container agg-rate-limit {
                tailf:info
                  "Configure the aggregate rate limit";
                tailf:cli-embed-no-on-delete;
                tailf:cli-compact-syntax;
                tailf:cli-sequence-commands;
                leaf agg-rate {
                  tailf:cli-drop-node-name;
                  tailf:cli-no-value-on-delete;
                  type union {
                    type uint32 {
                      range "1..40000000";
                    }
                    type enumeration {
                      enum "max";
                    }
                  }
                }
                leaf queue-frame-based-accounting {
                  tailf:cli-no-name-on-delete;
                  type empty;
                }
              }
              container filter {
                tailf:info
                  "Apply egress filter";
                tailf:cli-embed-no-on-delete;
                leaf ip {
                  type union {
                    type string {
                      length "1..64";
                    }
                    type uint16 {
                      range "1..65535";
                    }
                  }
                }
                leaf ipv6 {
                  type union {
                    type string {
                      length "1..64";
                    }
                    type uint16 {
                      range "1..65535";
                    }
                  }
                }
              }
              leaf policer-control-policy {
                tailf:info
                  "Specify policer control policy";
                tailf:cli-no-value-on-delete;
                tailf:non-strict-leafref {
                  path "/ncs:devices/ncs:device/ncs:config/alu:qos/policer-control-policy/name" {
                    tailf:xpath-root 3;
                  }
                }
                type string;
              }
              leaf qinq-mark-top-only {
                tailf:info
                  "Mark p-bits on top q-tag only";
                type empty;
              }
              leaf qos {
                tailf:info
                  "Apply egress qos policy";
                tailf:cli-embed-no-on-delete;
                type uint16;
                tailf:non-strict-leafref {
                  path "/ncs:devices/ncs:device/ncs:config/alu:qos/sap-egress/policy-id" {
                    tailf:xpath-root 3;
                  }
                }
              }
              container queue-override {
                tailf:info
                  "Apply queue override";
                tailf:cli-add-mode;
                uses queue-override-grouping;
              }
              leaf scheduler-policy {
                tailf:info
                  "Specify a scheduler-policy";
                tailf:cli-no-value-on-delete;
                tailf:non-strict-leafref {
                  path "/ncs:devices/ncs:device/ncs:config/alu:qos/scheduler-policy/scheduler-policy-name" {
                    tailf:xpath-root 3;
                  }
                }
                type string;
              }
            }
            container ingress {
              tailf:info
                "Configure ingress policies";
              tailf:cli-add-mode;
              leaf qos {
                tailf:cli-embed-no-on-delete;
                type uint16;
                tailf:non-strict-leafref {
                  path "/ncs:devices/ncs:device/ncs:config/alu:qos/sap-ingress/policy-id" {
                    tailf:xpath-root 3;
                  }
                }
              }
              container filter {
                tailf:info
                  "Apply ingress filter";
                tailf:cli-embed-no-on-delete;
                leaf ip {
                  type union {
                    type string {
                      length "1..64";
                    }
                    type uint16 {
                      range "1..65535";
                    }
                  }
                }
                leaf ipv6 {
                  type union {
                    type string {
                      length "1..64";
                    }
                    type uint16 {
                      range "1..65535";
                    }
                  }
                }
              }
              container queue-override {
                tailf:info
                  "Apply queue override";
                tailf:cli-add-mode;
                uses queue-override-grouping;
              }
            }
            leaf anti-spoof {
              tailf:info
                "Configures anti-spoof filtering for this SAP";
              type enumeration {
                enum "nh-mac";
              }
            }
            leaf multi-service-site {
              tailf:info
                "Specify the multi-service-site to which this SAP belongs";
              tailf:cli-embed-no-on-delete;
              type leafref {
                path "/ncs:devices/ncs:device/ncs:config/alu:service/customer/multi-service-site/customer-site-name" {
                  tailf:xpath-root 3;
                }
              }
            }
            container sub-sla-mgmt {
              presence "present";
              tailf:cli-add-mode;
              leaf def-sub-id {
                type enumeration {
                  enum "use-sap-id";
                }
              }
              leaf def-sub-profile {
                type string;
              }
              container single-sub-parameters {
                presence "present";
                tailf:cli-add-mode;
                leaf profiled-traffic-only {
                  type empty;
                }
              }
              leaf shutdown {
                tailf:cli-boolean-no;
                default "true";
                type boolean;
              }
            }
            leaf calling-station-id {
              tailf:info
                "Configure the RADIUS calling-station-id to include in auth/acct requests";
              type string;
            }
            leaf shutdown {
              tailf:info
                "Administratively enable/disable SAP";
              type empty;
            }
          }
          leaf tos-marking-state {
            tailf:info
              "Specify TOS marking state";
            tailf:cli-no-value-on-delete;
            tailf:cli-trim-default;
            type enumeration {
              enum "trusted";
              enum "untrusted";
            }
            default "untrusted";
          }
          container urpf-check {
            tailf:info
              "Enables/Configures unicast RPF check for an interface";
            tailf:cli-add-mode;
            leaf mode {
              tailf:cli-no-value-on-delete;
              type enumeration {
                enum "strict";
                enum "loose";
                enum "strict-no-ecmp";
              }
            }
          }
          leaf shutdown {
            tailf:info
              "Administratively enable/disable interface";
            type empty;
          }
        }
        leaf shutdown {
          tailf:cli-boolean-no;
          default "true";
          type boolean;
        }
      }
      list vpls {
        tailf:info
          "Provision a Virtual Private LAN Service";
        tailf:cli-recursive-delete;
        tailf:cli-diff-dependency "/alu:port" {
          tailf:xpath-root 3;
        }
        tailf:cli-diff-dependency "/alu:lag" {
          tailf:xpath-root 3;
        }
        key "service-id";
        leaf service-id {
          type vpls-id;
        }
        leaf customer {
          tailf:info
            "<customer-id>;;[1..2147483647]>";
          tailf:cli-hide-in-submode;
          tailf:cli-no-name-on-delete;
          tailf:cli-no-value-on-delete;
          type leafref {
            path "/ncs:devices/ncs:device/ncs:config/alu:service/customer/customer-id" {
              tailf:xpath-root 3;
            }
          }
        }
        leaf vpn {
          tailf:info
            "<vpn-id>;;[1..2147483647]";
          tailf:cli-hide-in-submode;
          type uint32 {
            range "1..2147483647";
          }
        }
        leaf m-vpls {
          tailf:info
            "<m-vpls>;;keyword - creates a management VPLS";
          tailf:cli-hide-in-submode;
          type empty;
        }
        choice a {
          leaf b-vpls {
            tailf:info
              "<b-vpls>;; keyword b-vpls - PBB backbone-vpls";
            tailf:cli-hide-in-submode;
            type empty;
          }
          leaf i-vpls {
            tailf:info
              "<i-vpls>;; keyword i-vpls - PBB backbone-vpls";
            tailf:cli-hide-in-submode;
            type empty;
          }
        }
        leaf description {
          tailf:info
            "Description for the service";
          tailf:cli-embed-no-on-delete;
          tailf:cli-no-value-on-delete;
          type string;
        }
        leaf disable-learning {
          tailf:info
            "Enable/disable learning of new MAC addresses";
          tailf:cli-embed-no-on-delete;
          type empty;
        }
        leaf disable-aging {
          tailf:info
            "Enable/disable aging of MAC addresses";
          tailf:cli-embed-no-on-delete;
          type empty;
        }
        leaf discard-unknown {
          tailf:cli-embed-no-on-delete;
          tailf:info
            "Enable/disable discarding of packets with unknown destination";
          type empty;
        }
        leaf allow-ip-int-binding {
          tailf:info
            "Enable/disable IP int binding";
          tailf:cli-embed-no-on-delete;
          type empty;
        }
        leaf service-name {
          tailf:info
            "Configure service name";
          tailf:cli-embed-no-on-delete;
          tailf:cli-no-value-on-delete;
          type string;
        }
        container eth-cfm {
          tailf:info
            "Configure CFM parameters";
          tailf:cli-add-mode;
          uses eth-cfm;
          leaf tunnel-fault {
            type enumeration {
              enum "accept";
              enum "ignore";
            }
          }
        }
        leaf fdb-table-high-wmark {
          tailf:info
            "Configure the high watermark for the FDB table";
          tailf:cli-embed-no-on-delete;
          tailf:cli-no-value-on-delete;
          type uint8 {
            range "0..100";
          }
        }
        leaf fdb-table-low-wmark {
          tailf:info
            "Configure the low watermark for the FDB table";
          tailf:cli-embed-no-on-delete;
          tailf:cli-no-value-on-delete;
          type uint8 {
            range "0..100";
          }
        }
        leaf fdb-table-size {
          tailf:info
            "Configure the maximum number of MAC entries in the FDB";
          tailf:cli-embed-no-on-delete;
          tailf:cli-no-value-on-delete;
          type uint32;
        }
        container igmp-snooping {
          tailf:info
            "Configure IGMP snooping parameters";
          tailf:cli-add-mode;
          leaf query-interval {
            tailf:info
              "Configure the IGMP Query Interval for v1/v2 Queriers";
            tailf:cli-embed-no-on-delete;
            tailf:cli-no-value-on-delete;
            type uint16 {
              range "0..1024";
            }
          }
          leaf report-src-ip {
            tailf:info
              "Configure the IP source address used in IGMP queries";
            tailf:cli-embed-no-on-delete;
            tailf:cli-no-value-on-delete;
            type inet:ipv4-address;
          }
          leaf robust-count {
            tailf:info
              "Configure the IGMP Robustness Variable for v1/v2 Queriers";
            tailf:cli-no-value-on-delete;
            type uint32;
          }
          leaf shutdown {
            tailf:info
              "Administratively enable or disable IGMP snooping";
            tailf:cli-boolean-no;
            default "true";
            type boolean;
          }
        }
        list interface {
          tailf:info
            "Create/delete or configure an IP interface";
          tailf:cli-embed-no-on-delete;
          key "ip-int-name";
          leaf ip-int-name {
            type string;
          }
          container address {
            tailf:info
              "Assigns an IP address/IP subnet/broadcast address format to the interface";
            tailf:cli-embed-no-on-delete;
            tailf:cli-sequence-commands;
            tailf:cli-compact-syntax;
            choice a {
              leaf addr-and-prefix {
                tailf:cli-drop-node-name;
                tailf:cli-no-value-on-delete;
                type tailf:ipv4-address-and-prefix-length;
              }
              case addr-and-netmask {
                leaf addr {
                  tailf:cli-drop-node-name;
                  tailf:cli-no-value-on-delete;
                  type inet:ipv4-address;
                }
                leaf mask {
                  tailf:cli-drop-node-name;
                  tailf:cli-no-value-on-delete;
                  type inet:ipv4-address;
                }
              }
            }
          }
          leaf arp-timeout {
            tailf:info
              "Configures timeout for an ARP entry learned on the interface";
            tailf:cli-no-value-on-delete;
            type uint16;
          }
          leaf description {
            tailf:info
              "Description for VPLS interface";
            tailf:cli-no-value-on-delete;
            type string;
          }
          leaf mac {
            tailf:info
              "Assign a MAC address to the interface";
            tailf:cli-no-value-on-delete;
            type ieee-mac;
          }
          list static-arp {
            tailf:info
              "Configure a static ARP entry for the interface";
            tailf:cli-suppress-mode;
            tailf:cli-sequence-commands;
            tailf:cli-embed-no-on-delete;
            key "address";
            leaf address {
              type inet:ipv4-address;
            }
            leaf ieee-address {
              tailf:info
                "xx:xx:xx:xx:xx:xx or xx-xx-xx-xx-xx-xx";
              tailf:cli-drop-node-name;
              type ieee-mac;
            }
            leaf unnumbered {
              type empty;
            }
          }
          leaf unnumbered {
            tailf:info
              "Configure the interface as an unnumbered interface";
            tailf:cli-no-value-on-delete;
            type union {
              type inet:ipv4-address;
              type string;
            }
          }
          leaf shutdown {
            tailf:info
              "Administratively enable/disable the interface";
            tailf:cli-boolean-no;
            default "true";
            type boolean;
          }
        }
        leaf local-age {
          tailf:info
            "Configure aging time for locally learned mac addresses";
          tailf:cli-embed-no-on-delete;
          tailf:cli-no-value-on-delete;
          type uint32 {
            range "60..86400";
          }
        }
        container mac-move {
          tailf:info
            "Configure Mac Move and its attributes";
          tailf:cli-embed-no-on-delete;
          tailf:cli-add-mode;
          leaf move-frequency {
            tailf:info
              "Configure move frequency to be used";
            tailf:cli-embed-no-on-delete;
            tailf:cli-no-value-on-delete;
            type uint8 {
              range "1..100";
            }
          }
          leaf retry-timeout {
            tailf:info
              "Configure retry timeout to be used";
            tailf:cli-embed-no-on-delete;
            tailf:cli-no-value-on-delete;
            type uint8 {
              range "0..120";
            }
          }
          leaf shutdown {
            tailf:info
              "Administratively enable/disable mac-move";
            tailf:cli-boolean-no;
            default "false";
            type boolean;
          }
        }
        leaf mfib-table-high-wmark {
          tailf:info
            "Configure the high watermark for the MFIB table";
          tailf:cli-embed-no-on-delete;
          tailf:cli-no-value-on-delete;
          type uint8 {
            range "1..100";
          }
        }
        leaf mfib-table-low-wmark {
          tailf:info
            "Configure the low watermark for the MFIB table";
          tailf:cli-embed-no-on-delete;
          tailf:cli-no-value-on-delete;
          type uint8 {
            range "1..100";
          }
        }
        leaf mfib-table-size {
          tailf:info
            "Configure the maximum number of SG entries in the MFIB";
          tailf:cli-embed-no-on-delete;
          tailf:cli-no-value-on-delete;
          type uint32;
        }
        leaf remote-age {
          tailf:info
            "Configure aging time for remotely learned mac addresses";
          tailf:cli-embed-no-on-delete;
          tailf:cli-no-value-on-delete;
          type uint32 {
            range "0..86400";
          }
        }
        leaf send-flush-on-failure {
          tailf:info
            "Enable/disable sending MAC withdraw message on SAP/Spoke-SDP failure";
          tailf:cli-embed-no-on-delete;
          type empty;
        }
        leaf service-mtu {
          tailf:info
            "Configure service MTU";
          tailf:cli-embed-no-on-delete;
          tailf:cli-no-value-on-delete;
          type uint16 {
            range "0..9194";
          }
        }
        list spb {
          tailf:info
            "Configure Shortest Path Bridging";
          tailf:cli-embed-no-on-delete;
          key "isis-instance";
          leaf isis-instance {
            tailf:info
              "<isis instance>;<1024..2047>";
            type uint16 {
              range "1024..2047";
            }
          }
          leaf fid {
            tailf:info
              "<fid>;;<1..4095>";
            tailf:cli-hide-in-submode;
            tailf:cli-no-name-on-delete;
            tailf:cli-no-value-on-delete;
            type uint16 {
              range "1..4095";
            }
          }
          list level {
            tailf:info
              "Configure SPB level information";
            tailf:cli-embed-no-on-delete;
            key "level";
            leaf level {
              type uint32;
            }
            leaf bridge-priority {
              tailf:info
                "Configure bridge priority";
              tailf:cli-no-name-on-delete;
              tailf:cli-no-value-on-delete;
              type uint8 {
                range "0..15";
              }
            }
            container ect-algorithm {
              tailf:info
                "Configure ECT algorithm of forwarding range";
              leaf fid-range {
                tailf:info
                  "<fid-range>;;<1..4095>-<1..4095>";
                tailf:cli-no-name-on-delete;
                tailf:cli-no-value-on-delete;
                type string;
              }
              leaf path-id {
                tailf:cli-no-name-on-delete;
                tailf:cli-drop-node-name;
                type enumeration {
                  enum "low-path-id";
                  enum "high-path-id";
                }
              }
            }
            container forwarding-tree-topology {
              tailf:info
                "Configure forwarding tree topology parameters";
              leaf unicast {
                tailf:cli-no-name-on-delete;
                type enumeration {
                  enum "spf";
                  enum "st";
                }
              }
            }
            leaf hello-interval {
              tailf:cli-embed-no-on-delete;
              tailf:cli-no-value-on-delete;
              type uint16 {
                range "0..20000";
              }
            }
            leaf hello-multiplier {
              tailf:cli-embed-no-on-delete;
              type uint8 {
                range "2..100";
              }
            }
            leaf metric {
              tailf:cli-embed-no-on-delete;
              tailf:cli-no-value-on-delete;
              type uint16;
            }
          }
          leaf lsp-pacing-interval {
            tailf:cli-embed-no-on-delete;
            tailf:cli-no-value-on-delete;
            type uint32;
          }
          leaf retransmit-interval {
            tailf:cli-embed-no-on-delete;
            type uint32;
          }
          leaf shutdown {
            tailf:info
              "Administratively enable or disable the operation of ISIS";
            tailf:cli-boolean-no;
            default "true";
            type boolean;
          }
        }
        container stp {
          tailf:cli-add-mode;
          leaf forward-delay {
            tailf:info
              "Configure forward-delay";
            tailf:cli-embed-no-on-delete;
            tailf:cli-no-value-on-delete;
            type uint8 {
              range "4..30";
            }
          }
          leaf hello-time {
            tailf:info
              "Configure hello-time";
            tailf:cli-embed-no-on-delete;
            tailf:cli-no-value-on-delete;
            type uint8 {
              range "1..10";
            }
          }
          leaf hold-count {
            tailf:info
              "Configure BPDU txmit hold count";
            tailf:cli-embed-no-on-delete;
            tailf:cli-no-value-on-delete;
            type uint8 {
              range "1..10";
            }
          }
          leaf max-age {
            tailf:info
              "Configure maximum info age for the stp";
            tailf:cli-embed-no-on-delete;
            tailf:cli-no-value-on-delete;
            type uint8 {
              range "6..40";
            }
          }
          leaf mode {
            tailf:info
              "Configure protocol version";
            tailf:cli-embed-no-on-delete;
            type enumeration {
              enum "rstp";
              enum "comp-dot1w";
              enum "dot1w";
              enum "mstp";
              enum "pmstp";
            }
          }
          list mst-instance {
            tailf:info
              "Provision a Multiple Spanning Tree instance";
            tailf:cli-embed-no-on-delete;
            key "mst-inst-number";
            leaf mst-inst-number {
              type uint16 {
                range "1..4094";
              }
            }
            leaf mst-priority {
              tailf:info
                "Configure the MST instance bridge priority";
              tailf:cli-embed-no-on-delete;
              tailf:cli-no-value-on-delete;
              type uint16;
            }
            leaf vlan-range {
              tailf:info
                "Configure range of VLANs managed by this MSTI";
              tailf:cli-embed-no-on-delete;
              tailf:cli-no-value-on-delete;
              type uint16 {
                range "0..4094";
              }
            }
          }
          leaf mst-max-hops {
            tailf:info
              "Configure the max number of hops in a MSTP region";
            tailf:cli-embed-no-on-delete;
            tailf:cli-no-value-on-delete;
            type uint8 {
              range "1..40";
            }
          }
          leaf mst-name {
            tailf:info
              "Configure the MST region name";
            tailf:cli-embed-no-on-delete;
            tailf:cli-no-value-on-delete;
            type string {
              length "1..32";
            }
          }
          leaf mst-revision {
            tailf:info
              "Configure MST configuration revision";
            tailf:cli-embed-no-on-delete;
            tailf:cli-no-value-on-delete;
            type uint16;
          }
          leaf priority {
            tailf:info
              "Configure bridge priority for the stp";
            tailf:cli-embed-no-on-delete;
            tailf:cli-no-value-on-delete;
            type uint16;
          }
          leaf shutdown {
            tailf:info
              "Enable/disable spanning tree protocol";
            tailf:cli-boolean-no;
            default "true";
            type boolean;
          }
        }
        leaf def-mesh-vc-id {
          tailf:info
            "Configure default mesh vc-id";
          tailf:cli-no-name-on-delete;
          tailf:cli-no-value-on-delete;
          type uint32 {
            range "1..4294967295";
          }
        }
        list mesh-sdp {
          tailf:cli-embed-no-on-delete;
          tailf:cli-key-format "$(1):$(2)";
          uses sdp-spoke-mesh-common;
          key "sdp-id vc-id";
        }
        container pim-snooping {
          tailf:cli-add-mode;
          leaf shutdown {
            tailf:cli-boolean-no;
            default "true";
            type boolean;
          }
        }
        list spoke-sdp {
          tailf:cli-embed-no-on-delete;
          tailf:cli-key-format "$(1):$(2)";
          uses sdp-spoke-mesh-common;
          key "sdp-id vc-id";
          leaf split-horizon-group {
            tailf:info
              "<group-name>";
            tailf:cli-hide-in-submode;
            tailf:cli-no-name-on-delete;
            tailf:cli-no-value-on-delete;
            type leafref {
              path "/ncs:devices/ncs:device/ncs:config/alu:service/vpls/split-horizon-group/group-name" {
                tailf:xpath-root 3;
              }
            }
          }
          leaf force-vlan-vc-forwarding {
            type empty;
          }
          leaf bpdu-translation {
            tailf:cli-embed-no-on-delete;
            type enumeration {
              enum "auto";
              enum "pvst";
              enum "stp";
            }
          }
          leaf diable-aging {
            tailf:cli-embed-no-on-delete;
            type empty;
          }
          leaf disable-learning {
            tailf:cli-embed-no-on-delete;
            type empty;
          }
          leaf discard-unknown-source {
            tailf:cli-embed-no-on-delete;
            type empty;
          }
          leaf l2pt-termination {
            tailf:cli-embed-no-on-delete;
            type empty;
          }
          leaf limit-mac-move {
            tailf:cli-embed-no-on-delete;
            tailf:cli-no-value-on-delete;
            type limit-mac-move;
          }
          leaf max-nbr-mac-addr {
            tailf:cli-embed-no-on-delete;
            tailf:cli-no-value-on-delete;
            type uint32;
          }
          container stp {
            tailf:cli-add-mode;
            uses stp-common;
          }
          container transit-policy {
            tailf:cli-embed-no-on-delete;
            leaf prefix {
              tailf:cli-no-value-on-delete;
              type uint16 {
                range "1..65535";
              }
            }
          }
        }
        list sap {
          tailf:info
            "Provision a SAP";
          tailf:cli-embed-no-on-delete;
          key "sap-id";
          leaf sap-id {
            tailf:info
              "<sap-id>;;different formats depending on port mode";
            tailf:cli-diff-dependency "/alu:service/ies/interface/sap[sap-id=current()/../sap-id]" {
              tailf:xpath-root 3;
              tailf:cli-trigger-on-set;
            }
            tailf:cli-diff-dependency "/alu:service/epipe/sap[sap-id=current()/../sap-id]" {
              tailf:xpath-root 3;
              tailf:cli-trigger-on-set;
            }
            tailf:cli-diff-dependency "/alu:service/vprn/interface/sap[sap-id=current()/../sap-id]" {
              tailf:xpath-root 3;
              tailf:cli-trigger-on-set;
            }
            tailf:cli-diff-dependency "/alu:service/vpls/sap[sap-id=current()/../sap-id]" {
              tailf:xpath-root 3;
              tailf:cli-trigger-on-set;
            }
            type string;
          }
          leaf split-horizon-group {
            tailf:info
              "<group-name>";
            tailf:cli-hide-in-submode;
            tailf:cli-no-name-on-delete;
            tailf:cli-no-value-on-delete;
            type leafref {
              path "/ncs:devices/ncs:device/ncs:config/alu:service/vpls/split-horizon-group/group-name" {
                tailf:xpath-root 3;
              }
            }
          }
          leaf accounting-policy {
            tailf:cli-embed-no-on-delete;
            tailf:cli-no-value-on-delete;
            type uint8 {
              range "1..99";
            }
          }
          leaf anti-spoof {
            tailf:info
              "Configures anti-spoof filtering for this SAP";
            tailf:cli-embed-no-on-delete;
            tailf:cli-no-value-on-delete;
            type enumeration {
              enum "ip";
              enum "ip-mac";
              enum "mac";
            }
          }
          leaf app-profile {
            tailf:info
              "Configure the application profile name";
            tailf:cli-embed-no-on-delete;
            tailf:cli-no-value-on-delete;
            type string {
              length "1..32";
            }
          }
          leaf auto-learn-mac-protect {
            tailf:info
              "Enable/disable automatic update of MAC protect list";
            tailf:cli-embed-no-on-delete;
            type empty;
          }
          leaf bpdu-translation {
            tailf:cli-embed-no-on-delete;
            type enumeration {
              enum "auto";
              enum "pvst";
              enum "stp";
            }
          }
          leaf collect-stats {
            tailf:info
              "Enable/disable statistics collection";
            tailf:cli-embed-no-on-delete;
            type empty;
          }
          leaf description {
            tailf:cli-embed-no-on-delete;
            tailf:cli-no-value-on-delete;
            type string;
          }
          leaf disable-aging {
            tailf:cli-embed-no-on-delete;
            type empty;
          }
          leaf disable-learning {
            tailf:cli-embed-no-on-delete;
            type empty;
          }
          leaf discard-unknown-source {
            tailf:cli-embed-no-on-delete;
            type empty;
          }
          container eth-cfm {
            tailf:cli-add-mode;
            uses eth-cfm;
            leaf mip {
              type empty;
            }
          }
          container igmp-snooping {
            uses igmp-snooping;
          }
          container ingress {
            tailf:cli-add-mode;
            uses sap-ingress-grouping;
          }
          leaf lag-link-map-profile {
            tailf:cli-embed-no-on-delete;
            tailf:cli-no-value-on-delete;
            type uint8 {
              range "1..32";
            }
          }
          leaf l2pt-termination {
            tailf:cli-embed-no-on-delete;
            type empty;
          }
          leaf limit-mac-move {
            tailf:cli-embed-no-on-delete;
            type limit-mac-move;
          }
          leaf mac-pinning {
            tailf:cli-embed-no-on-delete;
            type empty;
          }
          container managed-vlan-list {
            tailf:cli-add-mode;
            leaf default-sap {
              tailf:cli-embed-no-on-delete;
              type empty;
            }
            leaf range {
              tailf:cli-embed-no-on-delete;
              tailf:cli-no-value-on-delete;
              tailf:info
                "<vlan range>;;<0-4094>-<0-4094>";
              type string;
            }
          }
          leaf max-nbr-mac-addr {
            tailf:cli-embed-no-on-delete;
            tailf:cli-no-value-on-delete;
            type uint32 {
              range "1..4294967295";
            }
          }
          leaf monitor-oper-group {
            tailf:cli-embed-no-on-delete;
            tailf:cli-no-value-on-delete;
            tailf:non-strict-leafref {
              path "/ncs:devices/ncs:device/ncs:config/alu:service/oper-group/group-name" {
                tailf:xpath-root 3;
              }
            }
            type string;
          }
          leaf multi-service-site {
            tailf:cli-no-value-on-delete;
            type leafref {
              path "/ncs:devices/ncs:device/ncs:config/alu:service/customer/multi-service-site/customer-site-name" {
                tailf:xpath-root 3;
              }
            }
            tailf:cli-diff-dependency "../egress/scheduler-policy" {
              tailf:xpath-root 3;
              tailf:cli-trigger-on-set;
            }
          }
          container restrict-protected-src {
            tailf:info
              "Enable/disable protected src MAC restriction";
            tailf:cli-compact-syntax;
            tailf:cli-embed-no-on-delete;
            presence "present";
            leaf restrict-protected-src-value {
              tailf:cli-no-value-on-delete;
              tailf:cli-drop-node-name;
              type enumeration {
                enum "alarm-only";
                enum "discard-frame";
              }
            }
          }
          leaf restrict-unprotected-dst {
            tailf:info
              "Enable/disable unprotected dest MAC restriction";
            tailf:cli-embed-no-on-delete;
            type empty;
          }
          leaf ring-node {
            tailf:info
              "Configure a multi-chassis ring-node for this SAP";
            tailf:cli-embed-no-on-delete;
            type empty;
          }
          leaf static-mac {
            tailf:info
              "Configure a static mac entry";
            tailf:cli-embed-no-on-delete;
            tailf:cli-no-value-on-delete;
            type ieee-mac;
          }
          container egress {
            tailf:cli-add-mode;
            uses sap-egress-grouping;
          }
          container stp {
            tailf:info
              "Configure STP parameters";
            tailf:cli-add-mode;
            uses stp-common;
            list mst-instance {
              tailf:info
                "Provision a Multiple Spanning Tree instance";
              max-elements 1;
              key "mst-inst-number";
              leaf mst-inst-number {
                tailf:info
                  "<1..4094>";
                type uint16 {
                  range "1..4094";
                }
              }
              leaf mst-path-cost {
                tailf:info
                  "Configure path-cost";
                tailf:cli-no-name-on-delete;
                tailf:cli-no-value-on-delete;
                type uint32 {
                  range "1..200000000";
                }
              }
              leaf mst-priority {
                tailf:info
                  "Configure MSTI port priority";
                tailf:cli-no-name-on-delete;
                tailf:cli-no-value-on-delete;
                type uint32;
              }
            }
          }
          leaf tod-suite {
            tailf:cli-no-name-on-delete;
            tailf:cli-no-value-on-delete;
            type string;
          }
          leaf shutdown {
            type empty;
          }
        }
        list split-horizon-group {
          tailf:cli-embed-no-on-delete;
          tailf:info
            "Configure a split horizon group";
          key "group-name";
          leaf group-name {
            tailf:info
              "<group-name>;;<32 chars max>";
            type string {
              length "1..32";
            }
          }
          leaf residential-group {
            tailf:cli-hide-in-submode;
            tailf:cli-no-name-on-delete;
            type empty;
          }
          leaf auto-learn-mac-protect {
            tailf:info
              "Enable/disable automatic update of MAC protect list";
            tailf:cli-embed-no-on-delete;
            type empty;
          }
          leaf description {
            tailf:info
              "Description for this group";
            tailf:cli-embed-no-on-delete;
            tailf:cli-no-value-on-delete;
            type string;
          }
          leaf restrict-protected-src {
            tailf:info
              "Enable/disable protected src MAC restriction";
            tailf:cli-embed-no-on-delete;
            type empty;
          }
          leaf restrict-unprotected-src {
            tailf:info
              "Enable/disable unprotected src MAC restriction";
            tailf:cli-embed-no-on-delete;
            type empty;
          }
        }
        container bgp {
          tailf:info
            "Configure BGP";
          tailf:cli-recursive-delete;
          tailf:cli-add-mode;
          list pw-template-binding {
            tailf:info
              "Configure pw-template bind policy";
            key "policy-id";
            leaf policy-id {
              tailf:non-strict-leafref {
                path "/ncs:devices/ncs:device/ncs:config/alu:service/pw-template/policy-id" {
                  tailf:xpath-root 3;
                }
              }
              type uint16;
            }
          }
        }
        container bgp-ad {
          tailf:info
            "Configure BGP auto-discovery";
          tailf:cli-embed-no-on-delete;
          tailf:cli-add-mode;
          presence "true";
          leaf vpls-id {
            tailf:info
              "Configure VPLS-ID";
            type vpls-id;
          }
          leaf shutdown {
            tailf:info
              "Administratively enable/disable BGP auto-discovery";
            tailf:cli-boolean-no;
            default "true";
            type boolean;
          }
        }
        container bgp-vpls {
          tailf:cli-add-mode;
          tailf:cli-recursive-delete;
          leaf max-ve-id {
            tailf:cli-no-name-on-delete;
            tailf:cli-no-value-on-delete;
            tailf:info
              "Configure maximum vpls-edge id for BGP-VPLS";
            type uint16 {
              range "1..65535";
            }
          }
          container ve-name {
            tailf:info
              "Configure vpls-edge name for BGP-VPLS";
            tailf:cli-add-mode;
            tailf:cli-compact-syntax;
            leaf ve-name-value {
              tailf:cli-hide-in-submode;
              tailf:cli-drop-node-name;
              type string;
            }
            leaf ve-id {
              tailf:info
                "Configure vpls-edge identifier";
              tailf:cli-no-value-on-delete;
              type uint16 {
                range "1..65535";
              }
            }
          }
          leaf shutdown {
            tailf:info
              "Administratively Enable/Disable BGP-VPLS";
            type empty;
          }
        }
        leaf shutdown {
          tailf:info
            "Administratively enable/disable the service";
          tailf:cli-boolean-no;
          default "true";
          type boolean;
        }
      }
      list vprn {
        tailf:info
          "Provision a VPRN Service";
        tailf:cli-recursive-delete;
        tailf:cli-diff-dependency "/alu:port" {
          tailf:xpath-root 3;
        }
        tailf:cli-diff-dependency "/alu:lag" {
          tailf:xpath-root 3;
        }
        key "service-id";
        leaf service-id {
          type vpls-id;
        }
        leaf customer {
          tailf:info
            "<customer-id>;;[1..2147483647]>";
          tailf:cli-hide-in-submode;
          tailf:cli-no-name-on-delete;
          tailf:cli-no-value-on-delete;
          type leafref {
            path "/ncs:devices/ncs:device/ncs:config/alu:service/customer/customer-id" {
              tailf:xpath-root 3;
            }
          }
        }
        leaf auto-bind {
          tailf:cli-no-value-on-delete;
          type enumeration {
            enum "ldp";
            enum "gre";
            enum "rsvp-te";
            enum "mpls";
          }
        }
        container bgp {
          tailf:info
            "Create/Configure or delete BGP instance";
          tailf:cli-embed-no-on-delete;
          tailf:cli-recursive-delete;
          tailf:cli-add-mode;
          leaf damping {
            tailf:info
              "Enable/disable BGP route damping for learned routes asdefined within the route policy";
            type empty;
          }
          leaf router-id {
            tailf:cli-no-value-on-delete;
            type inet:ipv4-address;
          }
          list group {
            tailf:info
              "Configure a BGP group";
            tailf:cli-embed-no-on-delete;
            key "name";
            leaf name {
              type string;
            }
            leaf as-override {
              tailf:info
                "Enable/disable (group level) AS override";
              type empty;
            }
            container authentication-key {
              tailf:info
                "Configure the BGP authentication key for all peers";
              tailf:cli-embed-no-on-delete;
              tailf:cli-compact-syntax;
              tailf:cli-sequence-commands;
              leaf key {
                tailf:cli-drop-node-name;
                tailf:cli-no-value-on-delete;
                type string;
              }
              leaf type {
                tailf:cli-drop-node-name;
                tailf:cli-no-value-on-delete;
                type enumeration {
                  enum "hash";
                  enum "hash2";
                }
              }
            }
            leaf bfd-enable {
              tailf:info
                "enables BFD sessions on this group";
              type empty;
            }
            leaf description {
              tailf:info
                "Create a textual description for the group";
              tailf:cli-no-value-on-delete;
              type string;
            }
            leaf-list export {
              tailf:info
                "Export route policies used to determine which routes are advertised to peers for the group";
              tailf:cli-flat-list-syntax;
              tailf:cli-no-value-on-delete;
              tailf:non-strict-leafref {
                path "/ncs:devices/ncs:device/ncs:config/alu:router/policy-options/begin/policy-statement/name" {
                  tailf:xpath-root 3;
                }
              }
              max-elements 5;
              type string;
            }
            leaf-list import {
              tailf:info
                "Import route policies used to determine which routes are accepted from peers for this group";
              tailf:cli-flat-list-syntax;
              tailf:cli-no-value-on-delete;
              max-elements 5;
              type string;
            }
            leaf local-address {
              tailf:info
                "Local IP address used by the group when communicating with BGP peers";
              tailf:cli-no-value-on-delete;
              type inet:ipv4-address;
            }
            list neighbor {
              tailf:info
                "Configure a neighbor for this group";
              tailf:cli-embed-no-on-delete;
              key "address";
              leaf address {
                type union {
                  type inet:ipv4-address;
                  type inet:ipv6-address;
                }
              }
              leaf advertise-inactive {
                tailf:info
                  "Enable/disable advertising of inactive BGP routes to other BGP peers";
                type empty;
              }
              leaf description {
                tailf:info
                  "Create a textual description for the neighbor";
                tailf:cli-no-value-on-delete;
                type string;
              }
              leaf-list family {
                tailf:info
                  "Configure the IP family capability";
                tailf:cli-no-value-on-delete;
                tailf:cli-flat-list-syntax;
                type enumeration {
                  enum "ipv4";
                  enum "ipv6";
                }
              }
              leaf local-address {
                tailf:info
                  "Local IP address used by the neighbor when communicating with BGP peers";
                tailf:cli-no-value-on-delete;
                type union {
                  type inet:ipv4-address;
                  type inet:ipv6-address;
                }
              }
              leaf med-out {
                tailf:info
                  "Enable/disable advertising the Multi-Exit Discriminator (MED)";
                tailf:cli-no-value-on-delete;
                type union {
                  type uint32;
                  type enumeration {
                    enum "igp-cost";
                  }
                }
              }
              leaf multihop {
                tailf:cli-no-value-on-delete;
                type uint8 {
                  range "1..255";
                }
              }
              leaf peer-as {
                tailf:info
                  "Configure (neighbor level) the AS number for the remote peer";
                tailf:cli-no-value-on-delete;
                type uint32;
              }
              container remove-private {
                tailf:info
                  "Remove private AS numbers from the AS Path before advertising to the peers for this group";
                presence "true";
                leaf-list options {
                  tailf:cli-drop-node-name;
                  tailf:cli-flat-list-syntax;
                  tailf:cli-no-value-on-delete;
                  type enumeration {
                    enum "limited";
                    enum "skip-peer-as";
                  }
                }
              }
              leaf split-horizon {
                tailf:info
                  "Configure split horizon for the peer";
                type empty;
              }
              leaf type {
                tailf:info
                  "Configure the peers for this group as type internal or external";
                tailf:cli-no-value-on-delete;
                type enumeration {
                  enum "internal";
                  enum "external";
                }
              }
            }
            container prefix-limit {
              tailf:info
                "Maximum number of routes BGP can learn";
              tailf:cli-embed-no-on-delete;
              tailf:cli-compact-syntax;
              tailf:cli-sequence-commands;
              leaf limit {
                tailf:cli-drop-node-name;
                tailf:cli-no-value-on-delete;
                type uint32;
              }
              leaf log-only {
                tailf:cli-no-name-on-delete;
                type empty;
              }
              leaf treshold {
                tailf:cli-no-name-on-delete;
                tailf:cli-no-value-on-delete;
                type uint8 {
                  range "1..100";
                }
              }
              leaf idle-timeout {
                tailf:cli-no-name-on-delete;
                tailf:cli-no-value-on-delete;
                type union {
                  type uint16 {
                    range "0..1024";
                  }
                  type enumeration {
                    enum "forever";
                  }
                }
              }
            }
            leaf peer-as {
              tailf:info
                "Configure (group level) the AS number for the remote peer";
              tailf:cli-no-value-on-delete;
              type uint32;
            }
            container remove-private {
              tailf:info
                "Remove private AS numbers from the AS Path before advertising to the peers for this group";
              presence "true";
              leaf-list options {
                tailf:cli-drop-node-name;
                tailf:cli-flat-list-syntax;
                tailf:cli-no-value-on-delete;
                type enumeration {
                  enum "limited";
                  enum "skip-peer-as";
                }
              }
            }
            leaf type {
              tailf:info
                "Configure the peers for this group as type internal or external";
              tailf:cli-no-value-on-delete;
              type enumeration {
                enum "internal";
                enum "external";
              }
            }
            leaf shutdown {
              tailf:info
                "Administratively enable/disable the vprn bgp group";
              tailf:cli-boolean-no;
              default "true";
              type boolean;
            }
          }
          leaf med-out {
            tailf:info
              "Enable/disable advertising the Multi-Exit Discriminator (MED)";
            tailf:cli-no-value-on-delete;
            type union {
              type uint32;
              type enumeration {
                enum "igp-cost";
              }
            }
          }
          leaf min-route-advertisement {
            tailf:info
              "Minimum interval at which a given prefix is advertisedto a peer";
            tailf:cli-no-value-on-delete;
            type uint8 {
              range "1..255";
            }
          }
          leaf shutdown {
            tailf:info
              "Administratively enable/disable the vprn bgp";
            tailf:cli-boolean-no;
            default "false";
            type boolean;
          }
        }
        leaf description {
          tailf:cli-no-value-on-delete;
          type string;
        }
        container dhcp {
          tailf:info
            "Configure local DHCP servers for VPRN services";
          tailf:cli-add-mode;
          tailf:cli-recursive-delete;
          list local-dhcp-server {
            tailf:info
              "Configure the local DHCP server";
            tailf:cli-embed-no-on-delete;
            key "server-name";
            leaf server-name {
              type string;
            }
            leaf description {
              tailf:info
                "Description for this local DHCP server";
              tailf:cli-no-value-on-delete;
              type string;
            }
            leaf force-renews {
              tailf:info
                "Enable/disable sending FORCERENEW messages";
              type empty;
            }
            list pool {
              tailf:info
                "Configure an IP address pool";
              key "pool-id";
              leaf pool-id {
                type string {
                  length "1..32";
                }
              }
              leaf description {
                type string {
                  length "1..80";
                }
              }
              container max-lease-time {
                tailf:info
                  "Configure the maximum lease time";
                tailf:cli-compact-syntax;
                uses dhcp-lease-time;
              }
              container min-lease-time {
                tailf:info
                  "Configure the minimum lease time";
                tailf:cli-compact-syntax;
                uses dhcp-lease-time;
              }
              container minimum-free {
                tailf:info
                  "Configure the minimum number of free addresses";
                tailf:cli-compact-syntax;
                leaf minimum-free-value {
                  tailf:cli-drop-node-name;
                  type uint16 {
                    range "0..255";
                  }
                }
                leaf percent {
                  tailf:info
                    "Indicates the value indicates a percentage";
                  type empty;
                }
                leaf event-when-depleted {
                  type empty;
                }
              }
              leaf nak-non-matching-subnet {
                tailf:info
                  "Configure this server to reply with DHCPNAK to DHCPREQUEST for a subnet that does not match any range in this pool (rather than silently drop the request)";
                type empty;
              }
              container offer-time {
                leaf min {
                  type uint16 {
                    range "0..59";
                  }
                }
                leaf sec {
                  type uint16 {
                    range "0..59";
                  }
                }
              }
              container options {
                tailf:cli-add-mode;
                leaf-list dns-server {
                  tailf:info
                    "Configure the DNS server";
                  tailf:cli-flat-list-syntax;
                  tailf:cli-no-value-on-delete;
                  type inet:ipv4-address;
                }
                leaf domain-name {
                  tailf:info
                    "Configure the domain name";
                  type string {
                    length "1..127";
                  }
                }
                container lease-rebind-time {
                  tailf:info
                    "Configure the lease rebind time";
                  tailf:cli-compact-syntax;
                  uses dhcp-lease-time;
                }
                container lease-renew-time {
                  tailf:info
                    "Configure the lease renew time";
                  tailf:cli-compact-syntax;
                  uses dhcp-lease-time;
                }
                container lease-time {
                  tailf:info
                    "Configure the lease time";
                  tailf:cli-compact-syntax;
                  uses dhcp-lease-time;
                }
                leaf-list netbios-name-server {
                  tailf:info
                    "Configure the netbios name server";
                  tailf:cli-flat-list-syntax;
                  tailf:cli-no-value-on-delete;
                  type inet:ipv4-address;
                }
                leaf netbios-node-type {
                  tailf:info
                    "Configure the netbios node type";
                  type enumeration {
                    enum "B";
                    enum "P";
                    enum "M";
                    enum "H";
                  }
                }
              }
              list subnet {
                tailf:info
                  "Configure a subnet";
                key "subnet-id";
                leaf subnet-id {
                  type tailf:ipv4-address-and-prefix-length;
                }
                container address-range {
                  tailf:info
                    "Include range of IP addresses";
                  uses ip-address-range;
                }
                leaf drain {
                  tailf:info
                    "Configure the subnet draining";
                  type empty;
                }
                container exclude-addresses {
                  tailf:info
                    "Exclude range of IP addresses";
                  uses ip-address-range;
                }
                leaf maximum-declined {
                  tailf:info
                    "Configure the maximum number of declined addresses";
                  type uint32 {
                    range "0..4294967295";
                  }
                }
                container minimum-free {
                  tailf:info
                    "Configure the minimum number of free addresses";
                  leaf minimum-free-value {
                    tailf:cli-drop-node-name;
                    type uint16 {
                      range "0..255";
                    }
                  }
                  leaf percent {
                    tailf:info
                      "Indicates the value indicates a percentage";
                    type empty;
                  }
                  leaf event-when-depleted {
                    type empty;
                  }
                }
                container options {
                  tailf:cli-add-mode;
                  leaf-list default-router {
                    tailf:info
                      "Configure the default router";
                    tailf:cli-flat-list-syntax;
                    tailf:cli-no-value-on-delete;
                    type inet:ipv4-address;
                  }
                  leaf subnet-mask {
                    tailf:info
                      "Configure the subnet mask";
                    type inet:ipv4-address;
                  }
                }
              }
            }
            leaf shutdown {
              tailf:info
                "Administratively enable/disable the local DHCP server";
              tailf:cli-boolean-no;
              type boolean;
            }
          }
        }
        list interface {
          tailf:info
            "Create/delete or configure an IP interface";
          tailf:cli-recursive-delete;
          tailf:cli-embed-no-on-delete;
          key "ip-int-name";
          leaf ip-int-name {
            type string {
              length "1..32";
            }
          }
          leaf tunnel {
            tailf:cli-hide-in-submode;
            tailf:cli-no-name-on-delete;
            type empty;
          }
          leaf address {
            tailf:info
              "Assigns an IP address format to the interface";
            type tailf:ipv4-address-and-prefix-length;
          }
          container bfd {
            tailf:info
              "Configure BFD parameters";
            tailf:cli-embed-no-on-delete;
            tailf:cli-compact-syntax;
            tailf:cli-sequence-commands;
            leaf id {
              tailf:cli-drop-node-name;
              tailf:cli-no-value-on-delete;
              type uint32;
            }
            leaf receive {
              tailf:cli-no-name-on-delete;
              tailf:cli-no-value-on-delete;
              type uint32;
            }
            leaf multiplier {
              tailf:cli-no-name-on-delete;
              tailf:cli-no-value-on-delete;
              type uint32;
            }
            leaf type {
              tailf:cli-no-name-on-delete;
              tailf:cli-no-value-on-delete;
              type enumeration {
                enum "cpm-np";
              }
            }
          }
          container dhcp {
            tailf:cli-add-mode;
            leaf description {
              tailf:info
                "Add/remove a text description for DHCP";
              tailf:cli-no-value-on-delete;
              type string;
            }
            container gi-address {
              tailf:info
                "Configure the gateway interface address for the DHCP relay";
              tailf:cli-compact-syntax;
              leaf gi-address-value {
                tailf:cli-drop-node-name;
                tailf:cli-no-value-on-delete;
                type inet:ipv4-address;
              }
              leaf src-ip-addr {
                tailf:cli-no-value-on-delete;
                tailf:info
                  "Use the gi-address as src-ip";
                type empty;
              }
            }
            leaf lease-populate {
              tailf:info
                "Configure the maximum number of DHCPv4 leases";
              tailf:cli-no-value-on-delete;
              type uint16 {
                range "1..32767";
              }
            }
            leaf-list server {
              tailf:info
                "Configure the DHCP server IP address";
              tailf:cli-flat-list-syntax;
              tailf:cli-no-value-on-delete;
              type inet:ipv4-address;
            }
            leaf trusted {
              tailf:info
                "Enable/disable relaying of untrusted packets";
              type empty;
            }
            leaf use-arp {
              tailf:info
                "enable/disable the use of ARP to determine the destination Hw address";
              type empty;
            }
            leaf shutdown {
              tailf:info
                "Administratively enable/disable DHCP on this interface";
              tailf:cli-boolean-no;
              default "true";
              type boolean;
            }
          }
          leaf secondary {
            tailf:info
              "Assigns a secondary IP address format to the interface";
            type tailf:ipv4-address-and-prefix-length;
          }
          leaf description {
            tailf:cli-no-value-on-delete;
            type string;
          }
          leaf ip-mtu {
            tailf:info
              "Configure the interface IP MTU";
            tailf:cli-no-value-on-delete;
            type uint16;
          }
          leaf loopback {
            type empty;
          }
          list sap {
            tailf:info
              "Provision a SAP";
            tailf:cli-embed-no-on-delete;
            key "sap-id";
            leaf sap-id {
              tailf:info
                "<sap-id>;;different formats depending on port mode";
              tailf:cli-diff-dependency "/alu:service/ies/interface/sap[sap-id=current()/../sap-id]" {
                tailf:xpath-root 3;
                tailf:cli-trigger-on-set;
              }
              tailf:cli-diff-dependency "/alu:service/epipe/sap[sap-id=current()/../sap-id]" {
                tailf:xpath-root 3;
                tailf:cli-trigger-on-set;
              }
              tailf:cli-diff-dependency "/alu:service/vpls/sap[sap-id=current()/../sap-id]" {
                tailf:xpath-root 3;
                tailf:cli-trigger-on-set;
              }
              tailf:cli-diff-dependency "/alu:service/vprn/interface/sap[sap-id=current()/../sap-id]" {
                tailf:xpath-root 3;
                tailf:cli-trigger-on-set;
              }
              type string;
            }
            leaf accounting-policy {
              tailf:cli-no-value-on-delete;
              type uint8 {
                range "1..99";
              }
            }
            leaf anti-spoof {
              tailf:info
                "Configures anti-spoof filtering for this SAP";
              tailf:cli-no-value-on-delete;
              type enumeration {
                enum "ip";
                enum "ip-mac";
                enum "mac";
              }
            }
            leaf collect-stats {
              tailf:info
                "Enable/disable statistics collection";
              type empty;
            }
            leaf description {
              tailf:cli-no-value-on-delete;
              type string;
            }
            leaf multi-service-site {
              tailf:cli-no-value-on-delete;
              type leafref {
                path "/ncs:devices/ncs:device/ncs:config/alu:service/customer/multi-service-site/customer-site-name" {
                  tailf:xpath-root 3;
                }
              }
            }
            container egress {
              tailf:cli-add-mode;
              uses sap-egress-grouping;
            }
            container eth-cfm {
              tailf:cli-add-mode;
              uses eth-cfm;
            }
            container ingress {
              tailf:cli-add-mode;
              uses sap-ingress-grouping;
            }
            container ipsectunnel {
              tailf:cli-add-mode;
              uses sap-ingress-grouping;
            }
            leaf lag-link-map-profile {
              tailf:cli-no-value-on-delete;
              type uint8 {
                range "1..32";
              }
            }
            leaf shutdown {
              tailf:info
                "Administratively enable/disable the vprn interface sap";
              tailf:cli-boolean-no;
              default "true";
              type boolean;
            }
          }
          list spoke-sdp {
            tailf:cli-embed-no-on-delete;
            tailf:info
              "<sdp-id>:<vc-id>";
            tailf:cli-key-format "$(1):$(2)";
            uses sdp-common;
            key "sdp-id vc-id";
          }
          container urpf-check {
            tailf:cli-add-mode;
            leaf mode {
              tailf:cli-no-value-on-delete;
              type enumeration {
                enum "strict";
                enum "loose";
                enum "strict-no-encap";
              }
            }
          }
          list vpls {
            tailf:info
              "Configure vpls service";
            key "service-name";
            leaf service-name {
              type string;
            }
            container egress {
              tailf:info
                "Configure vpls egress parameters";
              tailf:cli-add-mode;
              leaf reclassify-using-qos {
                tailf:info
                  "Apply egress QoS policy";
                type string;
              }
            }
          }
          container ipv6 {
            tailf:cli-add-mode;
            tailf:info
              "Enables/Configures IPv6 for a VPRN interface";
            leaf address {
              tailf:info
                "Assigns an IPv6 address to the VPRN interface.";
              type tailf:ipv6-address-and-prefix-length;
            }
          }
          leaf shutdown {
            tailf:info
              "Administratively enable/disable the vprn interface";
            tailf:cli-boolean-no;
            default "true";
            type boolean;
          }
        }
        container ipsec {
          tailf:info
            "Configure IPsec Policies";
          tailf:cli-add-mode;
          list security-policy {
            tailf:info
              "Configure IPsec security policy";
            tailf:cli-embed-no-on-delete;
            key "security-policy-id";
            leaf security-policy-id {
              type uint32;
            }
            list entry {
              tailf:info
                "Configure IPsec security policy params";
              tailf:cli-embed-no-on-delete;
              key "entry-id";
              leaf entry-id {
                type uint8 {
                  range "1..16";
                }
              }
              leaf local-ip {
                tailf:info
                  "Configure local Ip prefix/mask for this policy param entry";
                tailf:cli-no-value-on-delete;
                type union {
                  type enumeration {
                    enum "any";
                  }
                  type tailf:ipv4-address-and-prefix-length;
                }
              }
              leaf local-v6-ip {
                tailf:info
                  "Configure local IPv6 prefix/mask for this policy param entry";
                tailf:cli-no-value-on-delete;
                type union {
                  type enumeration {
                    enum "any";
                  }
                  type tailf:ipv6-address-and-prefix-length;
                }
              }
              leaf remote-ip {
                tailf:info
                  "Configure remote Ip prefix/mask for this policy param entry";
                tailf:cli-no-value-on-delete;
                type union {
                  type enumeration {
                    enum "any";
                  }
                  type tailf:ipv4-address-and-prefix-length;
                }
              }
              leaf remote-v6-ip {
                tailf:info
                  "Configure remote IPv6 prefix/mask for this policy param entry";
                tailf:cli-no-value-on-delete;
                type union {
                  type enumeration {
                    enum "any";
                  }
                  type tailf:ipv6-address-and-prefix-length;
                }
              }
            }
          }
        }
        container maximum-routes {
          tailf:cli-embed-no-on-delete;
          tailf:cli-compact-syntax;
          leaf routes {
            tailf:cli-drop-node-name;
            tailf:cli-no-value-on-delete;
            type uint32;
          }
          leaf log-only {
            tailf:cli-no-value-on-delete;
            tailf:cli-no-name-on-delete;
            type empty;
          }
          leaf threshold {
            tailf:cli-no-value-on-delete;
            tailf:cli-no-name-on-delete;
            type uint8 {
              range "0..100";
            }
          }
        }
        leaf route-distinguisher {
          tailf:info
            "[ip-address:number1 | asn:number2]";
          tailf:cli-no-value-on-delete;
          tailf:cli-no-name-on-delete;
          type string;
        }
        leaf-list vrf-export {
          tailf:cli-flat-list-syntax;
          tailf:cli-no-value-on-delete;
          max-elements 15;
          type string;
        }
        leaf-list vrf-import {
          tailf:cli-flat-list-syntax;
          tailf:cli-no-value-on-delete;
          max-elements 15;
          type string;
        }
        container vrf-target {
          tailf:cli-embed-no-on-delete;
          choice vrf {
            leaf ext-community {
              tailf:cli-no-name-on-delete;
              type empty;
            }
            leaf export {
              tailf:cli-no-value-on-delete;
              tailf:cli-no-name-on-delete;
              type string;
            }
            leaf import {
              tailf:cli-no-value-on-delete;
              tailf:cli-no-name-on-delete;
              type string;
            }
            leaf ext-community-value {
              tailf:cli-drop-node-name;
              tailf:cli-no-value-on-delete;
              tailf:cli-no-name-on-delete;
              type string;
            }
          }
        }
        leaf autonomous-system {
          tailf:cli-no-value-on-delete;
          type uint32 {
            range "1..4294967295";
          }
        }
        list spoke-sdp {
          tailf:info
            "Configure spoke SDP bindings for VPRN services";
          key "sdp-id";
          leaf sdp-id {
            type uint32;
            tailf:non-strict-leafref {
              path "/ncs:devices/ncs:device/ncs:config/alu:service/sdp/sdp-id" {
                tailf:xpath-root 3;
              }
            }
          }
          leaf description {
            tailf:cli-no-value-on-delete;
            tailf:info
              "Description for this SAA test";
            type string {
              length "1..80";
            }
          }
        }
        list static-route {
          tailf:info
            "Creates/deletes static route entries";
          tailf:cli-compact-syntax;
          tailf:cli-sequence-commands;
          tailf:cli-embed-no-on-delete;
          tailf:cli-suppress-mode;
          key "route";
          leaf route {
            tailf:cli-drop-node-name;
            type union {
              type tailf:ipv4-address-and-prefix-length;
              type tailf:ipv6-address-and-prefix-length;
            }
          }
          choice nh {
            leaf next-hop {
              type union {
                type inet:ipv4-address;
                type inet:ipv6-address;
                type string;
              }
            }
            leaf indirect {
              type inet:ipv4-address;
            }
            leaf ipsec-tunnel {
              type string;
            }
            leaf black-hole {
              type empty;
            }
          }
          leaf preference {
            tailf:cli-break-sequence-commands;
            type uint8 {
              range "1..255";
            }
          }
          leaf metric {
            type uint16;
          }
          choice ed {
            leaf enable {
              type empty;
            }
            leaf disable {
              type empty;
            }
          }
          leaf tag {
            type uint32 {
              range "1..4294967295";
            }
          }
          leaf bfd-enable {
            tailf:info
              "enables BFD sessions on this static route";
            type empty;
          }
          leaf log {
            type empty;
          }
          leaf prefix-list-name {
            type string {
              length "1..32";
            }
          }
          choice an {
            leaf all {
              type empty;
            }
            leaf none {
              type empty;
            }
          }
        }
        container sgt-qos {
          tailf:info
            "Configure DSCP/Dot1p remarking for self-generated traffic";
          tailf:cli-add-mode;
          list application {
            tailf:info
              "Configure DSCP/Dot1p re-marking for applications";
            tailf:cli-suppress-mode;
            key "app-name";
            leaf app-name {
              type enumeration {
                enum "bgp";
                enum "pim";
                enum "ospf";
                enum "rip";
              }
            }
            leaf dscp {
              tailf:info
                "Configure DSCP name to FC mapping";
              type string;
            }
          }
        }
        container pim {
          tailf:info
            "Create/Configure or delete PIM instance";
          tailf:cli-add-mode;
          list interface {
            tailf:info
              "Configure PIM interface";
            key "name";
            leaf name {
              type string;
            }
          }
          container rp {
            tailf:info
              "Configure the router as static or Candidate-RP";
            tailf:cli-add-mode;
            container static {
              tailf:info
                "Context to configure static group to RP mapping";
              tailf:cli-add-mode;
              presence "true";
              list address {
                tailf:info
                  "Configure the RP address for mcast group prefixes";
                key "address";
                leaf address {
                  type union {
                    type inet:ipv4-address;
                    type inet:ipv6-address;
                  }
                }
                list group-prefix {
                  tailf:info
                    "Configure a group prefix for the RP address";
                  tailf:cli-suppress-mode;
                  key "address";
                  leaf address {
                    type tailf:ipv4-address-and-prefix-length;
                  }
                }
                leaf override {
                  tailf:info
                    "Change the precedence of static RP over dynamically learnt RP";
                  type empty;
                }
              }
            }
            container bsr-candidate {
              tailf:info
                "Context to configure Candidate Bootstrap parameters";
              tailf:cli-add-mode;
              leaf shutdown {
                tailf:cli-boolean-no;
                default "true";
                type boolean;
              }
            }
            container rp-candidate {
              tailf:info
                "Context to configure the Candidate RP parameters";
              tailf:cli-add-mode;
              leaf shutdown {
                tailf:cli-boolean-no;
                default "true";
                type boolean;
              }
            }
          }
        }
        container mvpn {
          tailf:info
            "Configure multicast VPN";
          tailf:cli-add-mode;
          leaf auto-discovery {
            tailf:info
              "Enable/disable multicast VPN membership auto-discovery";
            type enumeration {
              enum "default";
              enum "mdt-safi";
            }
          }
          leaf c-mcast-signaling {
            tailf:info
              "Specifies the protocol to use for PE-to-PE signaling";
            type enumeration {
              enum "bgp";
              enum "pim";
            }
          }
          container provider-tunnel {
            tailf:info
              "Configure provider tunnel for the multicast VPN";
            tailf:cli-add-mode;
            container inclusive {
              tailf:info
                "Configure inclusive provider tunnel for the mcast VPN";
              tailf:cli-add-mode;
              container pim {
                tailf:info
                  "Configure the PIM mode and group address for PIM based inclusive provider tunnels";
                tailf:cli-add-mode;
                presence "present";
                leaf multicast-type {
                  tailf:cli-drop-node-name;
                  type enumeration {
                    enum "asm";
                    enum "ssm";
                  }
                }
                leaf grp-ip-address {
                  tailf:cli-drop-node-name;
                  type inet:ipv4-address;
                }
                leaf shutdown {
                  tailf:cli-boolean-no;
                  default "true";
                  type boolean;
                }
              }
              container rsvp {
                tailf:info
                  "Enable/Disable the Context for specifiying RSVP P2MP LSP for the provider tunnel";
                tailf:cli-add-mode;
                leaf lsp-template {
                  type string;
                }
                leaf shutdown {
                  tailf:cli-boolean-no;
                  default "true";
                  type boolean;
                }
              }
            }
          }
          list vrf-target {
            tailf:info
              "Route target to be used for the multicast VPN";
            key "id";
            leaf id {
              type string;
            }
            leaf export {
              tailf:info
                "Specifies communitities to be sent to peers";
              type string;
            }
            leaf import {
              tailf:info
                "Specifies communitities to be accepted from peers";
              type string;
            }
          }
        }
        leaf router-id {
          tailf:info
            "Configure the router-id for the virtual router";
          type inet:ipv4-address;
        }
        list isis {
          key "id";
          leaf id {
            type uint32;
          }
          leaf area-id {
            type string;
          }
          leaf ipv6-routing {
            type enumeration {
              enum "native";
              enum "mt";
            }
          }
          container multi-topology {
            tailf:cli-add-mode;
            leaf ipv6-unicast {
              type empty;
            }
          }
          list interface {
            key "name";
            leaf name {
              type string;
            }
            leaf passive {
              type empty;
            }
            leaf interface-type {
              type enumeration {
                enum "point-to-point";
              }
            }
            leaf shutdown {
              tailf:cli-boolean-no;
              default "true";
              type boolean;
            }
          }
          leaf router-id {
            type inet:ipv4-address;
          }
          leaf shutdown {
            tailf:cli-boolean-no;
            default "true";
            type boolean;
          }
        }
        leaf shutdown {
          tailf:info
            "Administratively enable/disable the service";
          tailf:cli-boolean-no;
          default "true";
          type boolean;
        }
      }
      list pw-template {
        tailf:info
          "Configure a pseudowire template policy";
        tailf:cli-embed-no-on-delete;
        key "policy-id";
        leaf policy-id {
          type uint16;
        }
        leaf use-provisioned-sdp {
          tailf:cli-hide-in-submode;
          tailf:cli-no-name-on-delete;
          type empty;
        }
        leaf force-vlan-vc-forwarding {
          tailf:info
            "Forces vlan-vc-type forwarding in the data-path";
          type empty;
        }
        list split-horizon-group {
          tailf:cli-embed-no-on-delete;
          tailf:info
            "Configure a split horizon group";
          key "group-name";
          leaf group-name {
            tailf:info
              "<group-name>;;<32 chars max>";
            type string {
              length "1..32";
            }
          }
          leaf auto-learn-mac-protect {
            tailf:info
              "Enable/disable automatic update of MAC protect list";
            type empty;
          }
          leaf description {
            tailf:info
              "Description for this group";
            tailf:cli-no-value-on-delete;
            type string;
          }
          container restrict-protected-src {
            tailf:info
              "Enable/disable protected src MAC restriction";
            tailf:cli-embed-no-on-delete;
            presence "true";
            leaf option {
              tailf:cli-drop-node-name;
              tailf:cli-no-value-on-delete;
              tailf:cli-delete-container-on-delete;
              type enumeration {
                enum "alarm-only";
                enum "discard-frame";
              }
            }
          }
          leaf restrict-unprotected-dst {
            tailf:info
              "Enable/disable unprotected dst MAC restriction";
            type empty;
          }
        }
        leaf vc-type {
          tailf:info
            "Configure VC type";
          tailf:cli-no-name-on-delete;
          tailf:cli-no-value-on-delete;
          default "ether";
          type enumeration {
            enum "ether";
            enum "vlan";
          }
        }
      }
    }
    list router {
      tailf:ncs-device-type "cli-ned";
      tailf:display-when "not(../ncs:module) or ../ncs:module[ncs:name='tailf-ned-alu-sr']";
      tailf:info
        "Configure router instance";
      tailf:cli-recursive-delete;
      tailf:cli-embed-no-on-delete;
      key "router-name";
      leaf router-name {
        type string;
      }
      leaf autonomous-system {
        tailf:cli-no-value-on-delete;
        type uint32;
      }
      container bgp {
        tailf:info
          "Create/Configure or delete BGP instance";
        tailf:cli-add-mode;
        tailf:cli-embed-no-on-delete;
        presence "present";
        container add-paths {
          tailf:info
            "Enable/Disable BGP ADD-PATHS";
          tailf:cli-add-mode;
          tailf:cli-embed-no-on-delete;
          container ipv4 {
            tailf:info
              "Configure ipv4 ADD-PATH limits";
            tailf:cli-embed-no-on-delete;
            tailf:cli-compact-syntax;
            tailf:cli-sequence-commands;
            leaf send {
              tailf:cli-no-name-on-delete;
              tailf:cli-no-value-on-delete;
              type union {
                type uint8 {
                  range "1..16";
                }
                type enumeration {
                  enum "none";
                }
              }
            }
            leaf receive {
              tailf:cli-no-name-on-delete;
              tailf:cli-no-value-on-delete;
              type enumeration {
                enum "none";
              }
            }
          }
          container ipv6 {
            tailf:info
              "Configure ipv6 ADD-PATH limits";
            tailf:cli-embed-no-on-delete;
            tailf:cli-compact-syntax;
            tailf:cli-sequence-commands;
            leaf send {
              tailf:cli-no-name-on-delete;
              tailf:cli-no-value-on-delete;
              type union {
                type uint8 {
                  range "1..16";
                }
                type enumeration {
                  enum "none";
                }
              }
            }
            leaf receive {
              tailf:cli-no-name-on-delete;
              tailf:cli-no-value-on-delete;
              type enumeration {
                enum "none";
              }
            }
          }
          container vpn-ipv4 {
            tailf:info
              "Configure vpn-ipv4 ADD-PATH limits";
            tailf:cli-embed-no-on-delete;
            tailf:cli-compact-syntax;
            tailf:cli-sequence-commands;
            leaf send {
              tailf:cli-no-name-on-delete;
              tailf:cli-no-value-on-delete;
              type union {
                type uint8 {
                  range "1..16";
                }
                type enumeration {
                  enum "none";
                }
              }
            }
            leaf receive {
              tailf:cli-no-name-on-delete;
              tailf:cli-no-value-on-delete;
              type enumeration {
                enum "none";
              }
            }
          }
          container vpn-ipv6 {
            tailf:info
              "Configure vpn-ipv6 ADD-PATH limits";
            tailf:cli-embed-no-on-delete;
            tailf:cli-compact-syntax;
            tailf:cli-sequence-commands;
            leaf send {
              tailf:cli-no-name-on-delete;
              tailf:cli-no-value-on-delete;
              type union {
                type uint8 {
                  range "1..16";
                }
                type enumeration {
                  enum "none";
                }
              }
            }
            leaf receive {
              tailf:cli-no-name-on-delete;
              tailf:cli-no-value-on-delete;
              type enumeration {
                enum "none";
              }
            }
          }
        }
        leaf-list advertise-external {
          tailf:info
            "Enable/Disable Advertise Best External for the bgp family";
          tailf:cli-flat-list-syntax;
          type enumeration {
            enum "ipv4";
            enum "ipv6";
          }
        }
        leaf advertise-inactive {
          tailf:info
            "Enable/disable advertising of inactive BGP routes to other BGP peers";
          type empty;
        }
        leaf aggregator-id-zero {
          tailf:info
            "Enable/disable setting the router ID to 0 in the aggregator";
          type empty;
        }
        leaf auth-keychain {
          tailf:info
            "Configure TCP authentication keychain to use for the session";
          tailf:cli-no-value-on-delete;
          type string;
        }
        container authentication-key {
          tailf:info
            "Configure the BGP authentication key for all peers";
          tailf:cli-embed-no-on-delete;
          tailf:cli-compact-syntax;
          tailf:cli-sequence-commands;
          leaf key {
            tailf:cli-drop-node-name;
            tailf:cli-no-value-on-delete;
            type string;
          }
          leaf type {
            tailf:cli-drop-node-name;
            tailf:cli-no-value-on-delete;
            type enumeration {
              enum "hash";
              enum "hash2";
            }
          }
        }
        leaf-list backup-path {
          tailf:info
            "Enable/Disable Backup Path for the bgp family";
          tailf:cli-flat-list-syntax;
          type enumeration {
            enum "ipv4";
            enum "ipv6";
          }
        }
        container best-path-selection {
          tailf:info
            "Enable/Disable Path Selection Config";
          tailf:cli-add-mode;
          container always-compare-med {
            tailf:info
              "Determine how the Multi-Exit Discriminator (MED)";
            tailf:cli-compact-syntax;
            tailf:cli-embed-no-on-delete;
            leaf strict-as {
              tailf:cli-no-name-on-delete;
              type empty;
            }
            leaf type {
              tailf:cli-no-value-on-delete;
              tailf:cli-no-name-on-delete;
              type enumeration {
                enum "zero";
                enum "infinity";
              }
            }
          }
          leaf-list as-path-ignore {
            tailf:info
              "Determine whether the AS Path is used";
            tailf:cli-flat-list-syntax;
            tailf:cli-no-value-on-delete;
            type enumeration {
              enum "ipv4";
              enum "ipv6";
              enum "vpn-ipv4";
              enum "vpn-ipv6";
              enum "mcast-ipv4";
              enum "mvpn-ipv4";
              enum "l2-vpn";
              enum "mvpn-ipv6";
            }
          }
          leaf deterministic-med {
            tailf:info
              "Enable/Disable deterministic MED";
            type empty;
          }
          leaf ignore-nh-metric {
            tailf:info
              "Enable/Disable ignore next-hop metric";
            type empty;
          }
          leaf ignore-router-id {
            tailf:info
              "Enable/Disable ignore router-id";
            type empty;
          }
        }
        leaf bfd-enable {
          tailf:info
            "Enable BFD";
          type empty;
        }
        leaf cluster {
          tailf:info
            "Configure the cluster ID for a route reflector server";
          tailf:cli-no-value-on-delete;
          type inet:ipv4-address;
        }
        leaf connect-retry {
          tailf:info
            "Configure the BGP Connect Retry timer value";
          tailf:cli-no-value-on-delete;
          type uint16 {
            range "1..65535";
          }
        }
        leaf damping {
          tailf:info
            "Enable/disable BGP route damping for learned routes";
          type empty;
        }
        leaf description {
          tailf:info
            "Create a textual description stored in the configuration file";
          tailf:cli-no-value-on-delete;
          type string;
        }
        leaf disable-4byte-asn {
          tailf:info
            "Enable/disable the advertisement of 4-byte ASN";
          type empty;
        }
        leaf disable-client-reflect {
          tailf:info
            "Enable/disable the reflection of routes by the  route reflector at the global level";
          type empty;
        }
        leaf-list disable-communities {
          tailf:info
            "Configure BGP to disable sending communities";
          tailf:cli-no-value-on-delete;
          tailf:cli-flat-list-syntax;
          type enumeration {
            enum "standard";
            enum "extended";
          }
        }
        leaf disable-fast-external-failover {
          tailf:info
            "Configure BGP fast external failover";
          type empty;
        }
        leaf disable-route-table-install {
          tailf:info
            "Enable/Disable route table installation";
          type empty;
        }
        leaf enable-inter-as-vpn {
          tailf:info
            "Configure BGP to enable sending VPN routes across AS";
          type empty;
        }
        leaf enable-peer-tracking {
          tailf:info
            "Enable/disable BGP peer tracking";
          type empty;
        }
        leaf enable-rr-vpn-forwarding {
          tailf:info
            "Configure BGP to enable route-reflector";
          type empty;
        }
        leaf-list export {
          tailf:info
            "Export route policies used";
          tailf:cli-flat-list-syntax;
          tailf:cli-no-value-on-delete;
          type string;
        }
        leaf-list family {
          tailf:info
            "Configure the IP family capability";
          tailf:cli-flat-list-syntax;
          tailf:cli-no-value-on-delete;
          type enumeration {
            enum "ipv4";
            enum "vpn-ipv4";
            enum "ipv6";
            enum "vpn-ipv6";
            enum "mcast-ipv4";
            enum "l2-vpn";
            enum "mvpn-ipv4";
            enum "mdt-safi";
            enum "ms-pw";
            enum "flow-ipv4";
            enum "route-target";
            enum "mcast-vpn-ipv4";
            enum "mvpn-ipv6";
            enum "flow-ipv6";
          }
        }
        leaf flowspec-validate {
          tailf:info
            "Enable/Disable Flowspec Validation";
          type empty;
        }
        container graceful-restart {
          tailf:info
            "Enable/disable graceful-restart for all BGP peers";
          tailf:cli-add-mode;
          tailf:cli-embed-no-on-delete;
          leaf stale-routes-time {
            tailf:cli-no-value-on-delete;
            tailf:cli-no-name-on-delete;
            type uint16 {
              range "1..3600";
            }
          }
        }
        list group {
          tailf:info
            "Configure a BGP group";
          tailf:cli-embed-no-on-delete;
          key "id";
          leaf id {
            type string;
          }
          container add-paths {
            tailf:info
              "Enable/Disable BGP ADD-PATHS for the group";
            tailf:cli-add-mode;
            tailf:cli-embed-no-on-delete;
            container ipv4 {
              tailf:info
                "Configure ipv4 ADD-PATH limits";
              tailf:cli-embed-no-on-delete;
              tailf:cli-compact-syntax;
              tailf:cli-sequence-commands;
              leaf send {
                tailf:cli-no-name-on-delete;
                tailf:cli-no-value-on-delete;
                type union {
                  type uint8 {
                    range "1..16";
                  }
                  type enumeration {
                    enum "none";
                  }
                }
              }
              leaf receive {
                tailf:cli-no-name-on-delete;
                tailf:cli-no-value-on-delete;
                type enumeration {
                  enum "none";
                }
              }
            }
            container ipv6 {
              tailf:info
                "Configure ipv6 ADD-PATH limits";
              tailf:cli-embed-no-on-delete;
              tailf:cli-compact-syntax;
              tailf:cli-sequence-commands;
              leaf send {
                tailf:cli-no-name-on-delete;
                tailf:cli-no-value-on-delete;
                type union {
                  type uint8 {
                    range "1..16";
                  }
                  type enumeration {
                    enum "none";
                  }
                }
              }
              leaf receive {
                tailf:cli-no-name-on-delete;
                tailf:cli-no-value-on-delete;
                type enumeration {
                  enum "none";
                }
              }
            }
            container vpn-ipv4 {
              tailf:info
                "Configure vpn-ipv4 ADD-PATH limits";
              tailf:cli-embed-no-on-delete;
              tailf:cli-compact-syntax;
              tailf:cli-sequence-commands;
              leaf send {
                tailf:cli-no-name-on-delete;
                tailf:cli-no-value-on-delete;
                type union {
                  type uint8 {
                    range "1..16";
                  }
                  type enumeration {
                    enum "none";
                  }
                }
              }
              leaf receive {
                tailf:cli-no-name-on-delete;
                tailf:cli-no-value-on-delete;
                type enumeration {
                  enum "none";
                }
              }
            }
            container vpn-ipv6 {
              tailf:info
                "Configure vpn-ipv6 ADD-PATH limits";
              tailf:cli-embed-no-on-delete;
              tailf:cli-compact-syntax;
              tailf:cli-sequence-commands;
              leaf send {
                tailf:cli-no-name-on-delete;
                tailf:cli-no-value-on-delete;
                type union {
                  type uint8 {
                    range "1..16";
                  }
                  type enumeration {
                    enum "none";
                  }
                }
              }
              leaf receive {
                tailf:cli-no-name-on-delete;
                tailf:cli-no-value-on-delete;
                type enumeration {
                  enum "none";
                }
              }
            }
          }
          leaf advertise-inactive {
            tailf:info
              "Enable/disable advertising of inactive BGP routes";
            type empty;
          }
          leaf aggregator-id-zero {
            tailf:info
              "Enable/disable (group level) setting the router ID";
            type empty;
          }
          leaf aigp {
            tailf:info
              "Enable/Disable AIGP";
            type empty;
          }
          leaf auth-keychain {
            tailf:info
              "Configure TCP authentication keychain to use";
            tailf:cli-no-value-on-delete;
            type string;
          }
          container authentication-key {
            tailf:info
              "Configure the BGP authentication key for the group";
            tailf:cli-embed-no-on-delete;
            tailf:cli-compact-syntax;
            tailf:cli-sequence-commands;
            leaf key {
              tailf:cli-drop-node-name;
              tailf:cli-no-value-on-delete;
              type string;
            }
            leaf type {
              tailf:cli-drop-node-name;
              tailf:cli-no-value-on-delete;
              type enumeration {
                enum "hash";
                enum "hash2";
              }
            }
          }
          leaf bfd-enable {
            tailf:info
              "Enable BFD";
            type empty;
          }
          leaf cluster {
            tailf:info
              "Configure the cluster ID for a route reflector";
            tailf:cli-no-value-on-delete;
            type inet:ipv4-address;
          }
          leaf connect-retry {
            tailf:info
              "Configure the BGP Connect Retry timer value";
            tailf:cli-no-value-on-delete;
            type uint16 {
              range "1..65535";
            }
          }
          leaf damping {
            tailf:info
              "Enable/disable (group level) BGP route damping";
            type empty;
          }
          leaf default-route-target {
            tailf:info
              "Configure BGP group default route target";
            type empty;
          }
          leaf description {
            tailf:info
              "Create a textual description for the group";
            tailf:cli-no-value-on-delete;
            type string;
          }
          leaf disable-4byte-asn {
            tailf:info
              "Enable/disable the advertisement of 4-byte ASN";
            type empty;
          }
          leaf disable-capability-negotiation {
            tailf:info
              "Configure BGP group capability negotiation";
            type empty;
          }
          leaf disable-client-reflect {
            tailf:info
              "Enable/disable the reflection of routes";
            type empty;
          }
          leaf-list disable-communities {
            tailf:info
              "Configure BGP to disable sending communities";
            tailf:cli-no-value-on-delete;
            tailf:cli-flat-list-syntax;
            type enumeration {
              enum "standard";
              enum "extenden";
            }
          }
          leaf disable-fast-external-failover {
            tailf:info
              "Configure BGP fast external failover";
            type empty;
          }
          leaf enable-peer-tracking {
            tailf:info
              "Enable/disable BGP peer tracking";
            type empty;
          }
          leaf-list export {
            tailf:info
              "Export route policies used to determine routes";
            tailf:cli-no-value-on-delete;
            tailf:cli-flat-list-syntax;
            tailf:non-strict-leafref {
              path "/ncs:devices/ncs:device/ncs:config/alu:router/policy-options/begin/policy-statement/name" {
                tailf:xpath-root 3;
              }
            }
            type string;
          }
          leaf-list family {
            tailf:info
              "Configure the IP family capability";
            tailf:cli-flat-list-syntax;
            tailf:cli-no-value-on-delete;
            type enumeration {
              enum "ipv4";
              enum "vpn-ipv4";
              enum "ipv6";
              enum "vpn-ipv6";
              enum "mcast-ipv4";
              enum "l2-vpn";
              enum "mvpn-ipv4";
              enum "mdt-safi";
              enum "ms-pw";
              enum "flow-ipv4";
              enum "route-target";
              enum "mcast-vpn-ipv4";
              enum "mvpn-ipv6";
              enum "flow-ipv6";
            }
          }
          leaf flowspec-validate {
            tailf:info
              "Enable/Disable Flowspec Validation";
            type empty;
          }
          container graceful-restart {
            tailf:info
              "Enable/disable graceful-restart for BGP peer group";
            tailf:cli-add-mode;
            tailf:cli-embed-no-on-delete;
            leaf stale-routes-time {
              tailf:cli-no-value-on-delete;
              tailf:cli-no-name-on-delete;
              type uint16 {
                range "1..3600";
              }
            }
          }
          container hold-time {
            tailf:info
              "Configure BGP hold time";
            tailf:cli-compact-syntax;
            leaf seconds {
              tailf:cli-drop-node-name;
              tailf:cli-no-value-on-delete;
              type uint16 {
                range "3..65535";
              }
            }
            leaf min {
              tailf:cli-no-value-on-delete;
              tailf:cli-no-name-on-delete;
              type uint16 {
                range "3..65535";
              }
            }
          }
          leaf-list import {
            tailf:info
              "Import route policies used to determine routes";
            tailf:cli-no-value-on-delete;
            tailf:cli-flat-list-syntax;
            type string;
          }
          leaf keepalive {
            tailf:info
              "Configure BGP keepalive timer for the group";
            tailf:cli-no-value-on-delete;
            type uint16 {
              range "0..21845";
            }
          }
          leaf local-address {
            tailf:info
              "Local IP address used by the group";
            tailf:cli-no-value-on-delete;
            type union {
              type inet:ipv4-address;
              type inet:ipv6-address;
            }
          }
          container local-as {
            tailf:info
              "Add/remove a BGP virtual AS number";
            tailf:cli-embed-no-on-delete;
            tailf:cli-compact-syntax;
            tailf:cli-sequence-commands;
            leaf number {
              tailf:cli-no-value-on-delete;
              tailf:cli-no-name-on-delete;
              type uint32;
            }
            leaf private {
              tailf:cli-no-name-on-delete;
              type empty;
            }
            leaf no-prepend-global-as {
              tailf:cli-no-name-on-delete;
              type empty;
            }
          }
          leaf local-preference {
            tailf:info
              "Configure BGP local-preference attribute";
            tailf:cli-no-value-on-delete;
            type uint32;
          }
          leaf loop-detect {
            tailf:info
              "Configure (group level) how the BGP peer session";
            tailf:cli-no-value-on-delete;
            type enumeration {
              enum "drop-peer";
              enum "discard-route";
              enum "ignore-loop";
              enum "off";
            }
          }
          leaf med-out {
            tailf:info
              "Enable/disable (group level) advertising the MED";
            tailf:cli-no-value-on-delete;
            type union {
              type uint32;
              type enumeration {
                enum "igp-cost";
              }
            }
          }
          leaf min-as-origination {
            tailf:info
              "Minimum interval (group level) at which a given path";
            tailf:cli-no-value-on-delete;
            type uint8 {
              range "2..255";
            }
          }
          leaf min-route-advertisement {
            tailf:info
              "Minimum interval (group level) at which a prefix";
            tailf:cli-no-value-on-delete;
            type uint8 {
              range "2..255";
            }
          }
          leaf multihop {
            tailf:info
              "TTL value (group level) entered in the IP header";
            tailf:cli-no-value-on-delete;
            type uint8 {
              range "1..255";
            }
          }
          list neighbor {
            tailf:info
              "Configure a neighbor for this group";
            tailf:cli-embed-no-on-delete;
            key "address";
            leaf address {
              type union {
                type inet:ipv4-address;
                type inet:ipv6-address;
              }
            }
            leaf description {
              tailf:info
                "Create a textual description for the neighbor";
              tailf:cli-no-value-on-delete;
              type string;
            }
            container authentication-key {
              tailf:info
                "Configure the BGP authentication key for the peer";
              tailf:cli-embed-no-on-delete;
              tailf:cli-compact-syntax;
              tailf:cli-sequence-commands;
              leaf key {
                tailf:cli-drop-node-name;
                tailf:cli-no-value-on-delete;
                type string;
              }
              leaf hash {
                tailf:cli-drop-node-name;
                tailf:cli-no-value-on-delete;
                type enumeration {
                  enum "hash";
                  enum "hash2";
                }
              }
            }
            leaf peer-as {
              tailf:info
                "Configure (group level) the AS number";
              tailf:cli-no-value-on-delete;
              type uint32;
            }
            container remove-private {
              tailf:info
                "Remove private AS numbers from the AS Path";
              presence "true";
              leaf-list options {
                tailf:cli-drop-node-name;
                tailf:cli-flat-list-syntax;
                tailf:cli-no-value-on-delete;
                type enumeration {
                  enum "limited";
                  enum "skip-peer-as";
                }
              }
            }
            leaf shutdown {
              tailf:info
                "Administratively enable/disable the BGP neighbor";
              tailf:cli-boolean-no;
              default "true";
              type boolean;
            }
          }
          leaf next-hop-self {
            tailf:info
              "Configure the group to always set the nexthop path";
            type empty;
          }
          container outbound-route-filtering {
            tailf:info
              "Enable/disable outbound route filtering for this";
            tailf:cli-add-mode;
            container extended-community {
              tailf:info
                "Enable/disable outbound route filtering using extended communities";
              tailf:cli-add-mode;
              leaf accept-orf {
                tailf:info
                  "Enable/disable acceptance of ORFs";
                type empty;
              }
              leaf-list send-orf {
                tailf:info
                  "Add/Remove members to the send ORF list";
                tailf:cli-no-value-on-delete;
                tailf:cli-flat-list-syntax;
                type union {
                  type uint32;
                  type inet:ipv4-address;
                }
              }
            }
          }
          leaf passive {
            tailf:info
              "Enable/disable passive mode for the BGP group";
            type empty;
          }
          leaf path-mtu-discovery {
            tailf:info
              "Enable/Disable Path MTU Discovery";
            type empty;
          }
          leaf peer-as {
            tailf:info
              "Configure (group level) the AS number";
            tailf:cli-no-value-on-delete;
            type uint32;
          }
          leaf preference {
            tailf:info
              "Configure the route preference for routes";
            tailf:cli-no-value-on-delete;
            type uint8 {
              range "1..255";
            }
          }
          container prefix-limit {
            tailf:info
              "Maximum number of routes BGP can learn";
            tailf:cli-embed-no-on-delete;
            tailf:cli-compact-syntax;
            tailf:cli-sequence-commands;
            leaf limit {
              tailf:cli-drop-node-name;
              tailf:cli-no-value-on-delete;
              type uint32;
            }
            leaf log-only {
              tailf:cli-no-name-on-delete;
              type empty;
            }
            leaf treshold {
              tailf:cli-no-name-on-delete;
              tailf:cli-no-value-on-delete;
              type uint8 {
                range "1..100";
              }
            }
            leaf idle-timeout {
              tailf:cli-no-name-on-delete;
              tailf:cli-no-value-on-delete;
              type union {
                type uint16 {
                  range "0..1024";
                }
                type enumeration {
                  enum "forever";
                }
              }
            }
          }
          container remove-private {
            tailf:info
              "Remove private AS numbers from the AS Path";
            presence "true";
            leaf-list options {
              tailf:cli-drop-node-name;
              tailf:cli-flat-list-syntax;
              tailf:cli-no-value-on-delete;
              type enumeration {
                enum "limited";
                enum "skip-peer-as";
              }
            }
          }
          leaf split-horizon {
            tailf:info
              "Configure split horizon for the peers under this";
            type empty;
          }
          leaf ttl-security {
            tailf:info
              "Configure TTL security parameters for incoming";
            tailf:cli-no-value-on-delete;
            type uint8 {
              range "1..255";
            }
          }
          leaf type {
            tailf:info
              "Configure the peers for this group";
            tailf:cli-no-value-on-delete;
            type enumeration {
              enum "internal";
              enum "external";
            }
          }
          leaf vpn-apply-export {
            tailf:info
              "Enable/disable BGP VPN export policy";
            type empty;
          }
          leaf vpn-apply-import {
            tailf:info
              "Enable/disable BGP VPN import policy";
            type empty;
          }
          leaf shutdown {
            tailf:info
              "Administratively enable/disable the BGP group";
            tailf:cli-boolean-no;
            default "true";
            type boolean;
          }
        }
        container hold-time {
          tailf:info
            "Configure BGP hold time";
          tailf:cli-compact-syntax;
          leaf seconds {
            tailf:cli-drop-node-name;
            tailf:cli-no-value-on-delete;
            type uint16 {
              range "3..65535";
            }
          }
          leaf min {
            tailf:cli-no-value-on-delete;
            tailf:cli-no-name-on-delete;
            type uint16 {
              range "3..65535";
            }
          }
        }
        leaf ibgp-multipath {
          tailf:info
            "Define how IBGP routes with multiple next hops";
          type empty;
        }
        container igp-shortcut {
          tailf:info
            "Enables IGP shortcuts for BGP next-hop resolution";
          tailf:cli-embed-no-on-delete;
          tailf:cli-compact-syntax;
          tailf:cli-sequence-commands;
          leaf value {
            tailf:cli-drop-node-name;
            tailf:cli-no-value-on-delete;
            type enumeration {
              enum "ldp";
              enum "rsvp-te";
              enum "mpls";
            }
          }
          leaf disallow-igp {
            tailf:cli-no-name-on-delete;
            type empty;
          }
        }
        leaf-list import {
          tailf:info
            "Import route policies used to determine which routes";
          tailf:cli-no-value-on-delete;
          tailf:cli-flat-list-syntax;
          type string;
        }
        leaf keepalive {
          tailf:info
            "Configure BGP keepalive timer";
          tailf:cli-no-value-on-delete;
          type uint16 {
            range "0..21845";
          }
        }
        container local-as {
          tailf:info
            "Add/remove a BGP virtual AS number";
          tailf:cli-embed-no-on-delete;
          tailf:cli-compact-syntax;
          tailf:cli-sequence-commands;
          leaf number {
            tailf:cli-no-value-on-delete;
            tailf:cli-no-name-on-delete;
            type uint32;
          }
          leaf private {
            tailf:cli-no-name-on-delete;
            type empty;
          }
          leaf no-prepend-global-as {
            tailf:cli-no-name-on-delete;
            type empty;
          }
        }
        leaf local-preference {
          tailf:info
            "Configure BGP local-preference attribute in routes";
          tailf:cli-no-value-on-delete;
          type uint32;
        }
        leaf loop-detect {
          tailf:info
            "Configure how the BGP peer session handles loop detect";
          tailf:cli-no-value-on-delete;
          type enumeration {
            enum "drop-peer";
            enum "discard-route";
            enum "ignore-loop";
            enum "off";
          }
        }
        leaf med-out {
          tailf:info
            "Enable/disable advertising the Multi-Exit Discriminator";
          tailf:cli-no-value-on-delete;
          type union {
            type uint32;
            type enumeration {
              enum "igp-cost";
            }
          }
        }
        leaf min-as-origination {
          tailf:info
            "Minimum interval at which a given path attribute";
          tailf:cli-no-value-on-delete;
          type uint8 {
            range "2..255";
          }
        }
        leaf min-route-advertisement {
          tailf:info
            "Minimum interval at which a given prefix is advertised";
          tailf:cli-no-value-on-delete;
          type uint8 {
            range "1..255";
          }
        }
        leaf mp-bgp-keep {
          tailf:info
            "Enable/Disable Keep MP-BGP Routes Option";
          type empty;
        }
        leaf multihop {
          tailf:info
            "TTL value entered in the IP header of packets sent";
          tailf:cli-no-value-on-delete;
          type uint8 {
            range "1..255";
          }
        }
        leaf multipath {
          tailf:info
            "Configure multipath to share load traffic across";
          tailf:cli-no-value-on-delete;
          type uint8 {
            range "1..32";
          }
        }
        leaf mvpn-vrf-import-subtype-new {
          tailf:info
            "Configure Mvpn VRF Import sub-type under this instance";
          type empty;
        }
        container next-hop-resolution {
          tailf:info
            "Configure Next-hop Resolution";
          tailf:cli-add-mode;
          leaf policy {
            tailf:info
              "Configure Next-Hop Resolution policy";
            tailf:cli-no-value-on-delete;
            type string;
          }
          leaf use-bgp-routes {
            tailf:info
              "Enable/Disable Use BGP routes to resolve BGP nh";
            type empty;
          }
        }
        container outbound-route-filtering {
          tailf:info
            "Enable/disable outbound route filtering";
          tailf:cli-add-mode;
          container extended-community {
            tailf:info
              "Enable/disable outbound route filtering using extended communities";
            tailf:cli-add-mode;
            leaf accept-orf {
              tailf:info
                "Enable/disable acceptance of ORFs";
              type empty;
            }
            leaf-list send-orf {
              tailf:info
                "Add/Remove members to the send ORF list";
              tailf:cli-no-value-on-delete;
              tailf:cli-flat-list-syntax;
              type union {
                type uint32;
                type inet:ipv4-address;
              }
            }
          }
        }
        leaf path-mtu-discovery {
          tailf:info
            "Enable/disable Path MTU Discovery";
          type empty;
        }
        leaf peer-tracking-policy {
          tailf:info
            "Configure Peer-Tracking policy";
          tailf:cli-no-value-on-delete;
          type string;
        }
        leaf preference {
          tailf:info
            "Configure the route preference for routes learned";
          tailf:cli-no-value-on-delete;
          type uint8 {
            range "1..255";
          }
        }
        leaf purge-timer {
          tailf:info
            "Configure the maximum time before stale routes purged";
          tailf:cli-no-value-on-delete;
          type uint8 {
            range "1..60";
          }
        }
        leaf-list rapid-update {
          tailf:info
            "Enable/Disable BGP rapid update for addr-families";
          tailf:cli-flat-list-syntax;
          tailf:cli-no-value-on-delete;
          type enumeration {
            enum "l2-vpn";
            enum "mvpn-ipv4";
            enum "mdt-safi";
            enum "mvpn-ipv6";
          }
        }
        leaf rapid-withdrawal {
          tailf:info
            "Disable/Enable the delay on sending BGP rapid withdrawals";
          type empty;
        }
        leaf remove-private {
          tailf:info
            "Remove private AS numbers from the AS Path";
          tailf:cli-no-value-on-delete;
          type enumeration {
            enum "limited";
            enum "skip-peer-as";
          }
        }
        leaf-list route-target-list {
          tailf:info
            "Add/Remove members to a route-target-list";
          tailf:cli-no-value-on-delete;
          tailf:cli-flat-list-syntax;
          type union {
            type uint32;
            type inet:ipv4-address;
          }
        }
        leaf router-id {
          tailf:info
            "Configure the router ID to be used with this BGP instance";
          tailf:cli-no-value-on-delete;
          type union {
            type inet:ipv4-address;
            type inet:ipv6-address;
          }
        }
        leaf split-horizon {
          tailf:info
            "Configure split horizon for the peers under this instance";
          type empty;
        }
        leaf transport-tunnel {
          tailf:info
            "Enable mechanism to be used for transport";
          tailf:cli-no-value-on-delete;
          type enumeration {
            enum "ldp";
            enum "rsvp-te";
            enum "mpls";
          }
        }
        leaf vpn-apply-export {
          tailf:info
            "Enable/disable BGP VPN export policy";
          type empty;
        }
        leaf vpn-apply-import {
          tailf:info
            "Enable/disable BGP VPN import policy";
          type empty;
        }
        leaf shutdown {
          tailf:info
            "Administratively enable/disable the BGP instance";
          tailf:cli-boolean-no;
          default "false";
          type boolean;
        }
      }
      leaf ecmp {
        tailf:info
          "Enable/disable ECMP and configure max number of routes for path sharing";
        tailf:cli-no-value-on-delete;
        type uint8 {
          range "0..32";
        }
      }
      leaf fib-priority {
        tailf:info
          "Specify the FIB Priority";
        type enumeration {
          enum "high";
          enum "standard";
        }
      }
      leaf ldp-shortcut {
        tailf:info
          "Allow IGP route resolution using LDP LSPs across network interfaces participating in IS-IS and OSPF";
        tailf:cli-no-value-on-delete;
        default "ipv4";
        type enumeration {
          enum "ipv4";
          enum "ipv6";
        }
      }
      leaf router-id {
        tailf:cli-no-value-on-delete;
        type inet:ipv4-address;
      }
      list static-route {
        tailf:info
          "Creates/deletes static route entries";
        tailf:cli-compact-syntax;
        tailf:cli-sequence-commands;
        tailf:cli-embed-no-on-delete;
        tailf:cli-delete-when-empty;
        tailf:cli-suppress-mode;
        key "route";
        leaf route {
          type union {
            type tailf:ipv4-address-and-prefix-length;
            type tailf:ipv6-address-and-prefix-length;
          }
        }
        choice nh {
          leaf next-hop {
            type union {
              type inet:ipv4-address;
              type inet:ipv6-address;
              type string;
            }
          }
          leaf indirect {
            type inet:ipv4-address;
          }
          leaf black-hole {
            type empty;
          }
        }
        leaf preference {
          tailf:cli-break-sequence-commands;
          type uint8 {
            range "1..255";
          }
        }
        leaf metric {
          type uint16;
        }
        choice ed {
          leaf enable {
            type empty;
          }
          leaf disable {
            type empty;
          }
        }
        leaf ldp {
          type empty;
        }
        leaf disallow-igp {
          type empty;
        }
        leaf tag {
          type uint32 {
            range "1..4294967295";
          }
        }
        leaf bfd-enable {
          tailf:info
            "enables BFD sessions on this static route";
          type empty;
        }
        leaf mcast-family {
          type enumeration {
            enum "mcast-ipv4";
            enum "mcast-ipv6";
          }
        }
        leaf rsvp-te {
          type empty;
        }
        leaf cpe-ip-address {
          type inet:ipv4-address;
        }
        leaf seconds {
          type uint8 {
            range "1..255";
          }
        }
        leaf count {
          type uint8 {
            range "1..255";
          }
        }
        leaf log {
          type empty;
        }
        leaf prefix-list-name {
          type string {
            length "1..32";
          }
        }
        choice an {
          leaf all {
            type empty;
          }
          leaf none {
            type empty;
          }
        }
        leaf ldp-sync {
          type empty;
        }
        leaf fc-name {
          type enumeration {
            enum "be";
            enum "l2";
            enum "af";
            enum "l1";
            enum "h2";
            enum "ef";
            enum "h1";
            enum "nc";
          }
        }
        choice lh {
          leaf low {
            type empty;
          }
          leaf high {
            type empty;
          }
        }
      }
      list isis {
        tailf:info
          "Create/Configure or delete ISIS instance";
        tailf:cli-embed-no-on-delete;
        key "id";
        leaf id {
          type uint32;
        }
        leaf all-l1isis {
          tailf:info
            "Specify the MAC address to use for All L1 ISIS routers";
          tailf:cli-no-value-on-delete;
          type string;
        }
        leaf all-l2isis {
          tailf:info
            "Specify the MAC address to use for All L2 ISIS routers";
          tailf:cli-no-value-on-delete;
          type string;
        }
        leaf area-id {
          tailf:info
            "Configure an area-id used by ISIS (upto 13 bytes)";
          type string;
        }
        leaf iid-tlv-enable {
          tailf:info
            "Enable use of IID TLV for this ISIS instance";
          type empty;
        }
        leaf ipv4-routing {
          tailf:info
            "Enable/Disable IPv4 routing";
          type empty;
        }
        leaf ipv4-multicast-routing {
          tailf:info
            "Enable/Disable IPv4 routing";
          tailf:cli-no-value-on-delete;
          type enumeration {
            enum "native";
            enum "mt";
          }
        }
        leaf ipv6-routing {
          tailf:info
            "Enable/Disable IPv6 routing";
          tailf:cli-no-value-on-delete;
          type enumeration {
            enum "native";
            enum "mt";
          }
        }
        leaf ipv6-multicast-routing {
          tailf:info
            "Enable/Disable IPv6 multicast-routing";
          tailf:cli-no-value-on-delete;
          type enumeration {
            enum "native";
            enum "mt";
          }
        }
        leaf lsp-lifetime {
          tailf:info
            "Configure LSP lifetime";
          tailf:cli-no-value-on-delete;
          type uint16 {
            range "350..65535";
          }
        }
        leaf lsp-refresh-interval {
          tailf:info
            "Configure LSP refresh interval";
          type uint32;
        }
        container lsp-wait {
          tailf:info
            "Configure ISIS LSP wait times";
          tailf:cli-embed-no-on-delete;
          tailf:cli-compact-syntax;
          tailf:cli-sequence-commands;
          leaf wait {
            tailf:cli-drop-node-name;
            tailf:cli-no-value-on-delete;
            type uint8 {
              range "1..120";
            }
          }
          leaf initial-wait {
            tailf:cli-drop-node-name;
            tailf:cli-no-value-on-delete;
            type uint8 {
              range "0..100";
            }
          }
          leaf second-wait {
            tailf:cli-drop-node-name;
            tailf:cli-no-value-on-delete;
            type uint8 {
              range "1..100";
            }
          }
        }
        list level {
          tailf:info
            "Configure the default global parameters both level one and two interfaces";
          key "id";
          leaf id {
            type enumeration {
              enum "1";
              enum "2";
            }
          }
          container authentication-key {
            tailf:info
              "Configure the authentication-key to be used";
            tailf:cli-embed-no-on-delete;
            tailf:cli-compact-syntax;
            tailf:cli-sequence-commands;
            leaf key {
              tailf:cli-drop-node-name;
              tailf:cli-no-value-on-delete;
              type string;
            }
            leaf keyword {
              tailf:cli-drop-node-name;
              tailf:cli-no-value-on-delete;
              type enumeration {
                enum "hash";
                enum "hash2";
              }
            }
          }
          leaf authentication-type {
            tailf:info
              "Configure the authentication type to be used";
            tailf:cli-no-value-on-delete;
            type enumeration {
              enum "password";
              enum "message-digest";
            }
          }
          leaf csnp-authentication {
            tailf:info
              "Enable/disable authentication per CSNP message type at ISIS level.";
            type empty;
          }
          leaf default-ipv6-unicast-metric {
            tailf:info
              "Configure default metric for IPv6 unicast";
            tailf:cli-no-value-on-delete;
            type uint32 {
              range "1..16777215";
            }
          }
          leaf default-metric {
            tailf:info
              "Configure default metric for IPv4 unicast";
            tailf:cli-no-value-on-delete;
            type uint32 {
              range "1..16777215";
            }
          }
          leaf external-preference {
            tailf:info
              "Configure external-preference";
            tailf:cli-no-value-on-delete;
            type uint8 {
              range "1..255";
            }
          }
          leaf hello-authentication {
            tailf:info
              "Enable/disable authentication per HELLO message type at ISIS level.";
            type empty;
          }
          leaf loopfree-alternate-exclude {
            tailf:info
              "Enable/disable LFA at ISIS level.";
            type empty;
          }
          leaf preference {
            tailf:info
              "Configure preference";
            tailf:cli-no-value-on-delete;
            type uint8 {
              range "1..255";
            }
          }
          leaf psnp-authentication {
            tailf:info
              "Enable/disable authentication per PSNP message type at ISIS level.";
            type empty;
          }
          leaf wide-metrics-only {
            tailf:info
              "Enable/disable wide-metrics advertisements in the LSPs";
            type empty;
          }
        }
        list link-group {
          tailf:cli-embed-no-on-delete;
          key "name";
          leaf name {
            type string;
          }
          list level {
            tailf:cli-embed-no-on-delete;
            key "id";
            leaf id {
              type enumeration {
                enum "1";
                enum "2";
              }
            }
            leaf ipv6-unicast-metric-offset {
              tailf:cli-no-value-on-delete;
              type uint8;
            }
            list member {
              tailf:cli-suppress-mode;
              key "name";
              leaf name {
                type string;
              }
            }
            leaf revert-members {
              tailf:cli-no-value-on-delete;
              type uint32;
            }
            leaf oper-members {
              tailf:cli-no-value-on-delete;
              type uint32;
            }
          }
        }
        container multi-topology {
          tailf:info
            "Enable/disable IS-IS multi-topology support";
          tailf:cli-add-mode;
          leaf ipv6-unicast {
            tailf:cli-embed-no-on-delete;
            type empty;
          }
        }
        list interface {
          tailf:info
            "Configure ISIS interface";
          tailf:cli-embed-no-on-delete;
          tailf:cli-recursive-delete;
          key "name";
          leaf name {
            tailf:non-strict-leafref {
              path "/ncs:devices/ncs:device/ncs:config/alu:router/interface/interface-name" {
                tailf:xpath-root 3;
              }
            }
            type string;
          }
          leaf bfd-enable {
            tailf:info
              "Enable-BFD";
            type enumeration {
              enum "ipv4";
              enum "ipv6";
            }
          }
          leaf csnp-interval {
            tailf:info
              "Configure the frequency that CSN packets are sent from this interface";
            type uint16 {
              range "1..65535";
            }
          }
          leaf hello-authentication {
            tailf:info
              "Enable/disable hello-authentication on the interface";
            type empty;
          }
          container hello-authentication-key {
            tailf:info
              "Configure the authentication-key";
            tailf:cli-embed-no-on-delete;
            tailf:cli-sequence-commands;
            tailf:cli-compact-syntax;
            leaf key {
              tailf:cli-drop-node-name;
              tailf:cli-no-value-on-delete;
              type string;
            }
            leaf type {
              tailf:cli-drop-node-name;
              tailf:cli-no-value-on-delete;
              type enumeration {
                enum "hash";
                enum "hash2";
              }
            }
          }
          leaf hello-authentication-type {
            tailf:info
              "Configure hello-authentication-type to be enabled";
            tailf:cli-no-value-on-delete;
            type enumeration {
              enum "password";
              enum "message-digest";
            }
          }
          leaf interface-type {
            tailf:info
              "Configure the interface type";
            tailf:cli-no-value-on-delete;
            type enumeration {
              enum "broadcast";
              enum "point-to-point";
            }
          }
          leaf ipv4-multicast-enable {
            tailf:info
              "Disable IS-IS IPv4 multicast routing for the interface";
            type empty;
          }
          leaf ipv6-multicast-enable {
            tailf:info
              "Disable IS-IS IPv6 multicast routing for the interface";
            type empty;
          }
          leaf ipv6-unicast-enable {
            tailf:info
              "Disable IS-IS IPv6 unicast routing for the interface";
            type empty;
          }
          list level {
            tailf:info
              "Configure the default parameters for level one and two interfaces";
            tailf:cli-embed-no-on-delete;
            key "id";
            leaf id {
              type uint8 {
                range "1..2";
              }
            }
            container hello-authentication-key {
              tailf:info
                "Configure the authentication-key";
              tailf:cli-embed-no-on-delete;
              tailf:cli-sequence-commands;
              tailf:cli-compact-syntax;
              leaf key {
                tailf:cli-drop-node-name;
                tailf:cli-no-value-on-delete;
                type string;
              }
              leaf type {
                tailf:cli-drop-node-name;
                tailf:cli-no-value-on-delete;
                type enumeration {
                  enum "hash";
                  enum "hash2";
                }
              }
            }
            leaf hello-authentication-type {
              tailf:info
                "Configure hello-authentication-type to be enabled";
              tailf:cli-no-value-on-delete;
              type enumeration {
                enum "password";
                enum "message-digest";
              }
            }
            leaf hello-interval {
              tailf:info
                "Configure hello-interval for this interface";
              tailf:cli-no-value-on-delete;
              type uint16 {
                range "1..20000";
              }
            }
            leaf hello-multiplier {
              tailf:info
                "Configure hello-multiplier for this level";
              tailf:cli-no-value-on-delete;
              type uint8 {
                range "2..100";
              }
            }
            leaf ipv4-multicast-metric {
              tailf:info
                "Configure IS-IS interface metric for IPv4 multicast";
              tailf:cli-no-value-on-delete;
              type uint32 {
                range "1..16777215";
              }
            }
            leaf ipv6-multicast-metric {
              tailf:info
                "Configure IS-IS interface metric for IPv6 multicast";
              tailf:cli-no-value-on-delete;
              type uint32 {
                range "1..16777215";
              }
            }
            leaf ipv6-unicast-metric {
              tailf:info
                "Configure IS-IS interface metric for IPv6 unicast";
              tailf:cli-no-value-on-delete;
              type uint32 {
                range "1..16777215";
              }
            }
            leaf metric {
              tailf:info
                "Configure IS-IS interface metric for IPv4 unicast";
              tailf:cli-no-value-on-delete;
              type uint32 {
                range "1..16777215";
              }
            }
            leaf passive {
              tailf:info
                "Configure passive";
              type empty;
            }
            leaf priority {
              tailf:info
                "Configure the priority that serves to determine router";
              tailf:cli-no-value-on-delete;
              type uint8 {
                range "0..127";
              }
            }
            leaf sd-offset {
              tailf:info
                "Configure the signal degrade offset";
              tailf:cli-no-value-on-delete;
              type uint32 {
                range "1..16777215";
              }
            }
            leaf sf-offset {
              tailf:info
                "Configure the signal fail offset";
              tailf:cli-no-value-on-delete;
              type uint32 {
                range "1..16777215";
              }
            }
          }
          leaf level-capability {
            tailf:info
              "Specifies ISIS levels for this interface";
            tailf:cli-no-value-on-delete;
            type enumeration {
              enum "level-1";
              enum "level-2";
              enum "level-1/2";
            }
          }
          leaf loopfree-alternate-exclude {
            tailf:info
              "Enable/disable LFA for ISIS on this interface";
            type empty;
          }
          leaf lsp-pacing-interval {
            tailf:info
              "Configure the interval between LSP packets are sent";
            tailf:cli-no-value-on-delete;
            type uint16;
          }
          leaf mesh-group {
            tailf:info
              "Configure mesh groups";
            tailf:cli-no-value-on-delete;
            type union {
              type uint32 {
                range "1..2000000000";
              }
              type enumeration {
                enum "blocked";
              }
            }
          }
          leaf passive {
            tailf:info
              "Configure passive interface";
            type empty;
          }
          leaf retransmit-interval {
            tailf:info
              "Configure the minimum interval between LSP retrans";
            tailf:cli-no-value-on-delete;
            type uint16 {
              range "1..65535";
            }
          }
          leaf tag {
            tailf:info
              "Configure a route tag to the IP addr of an interface";
            tailf:cli-no-value-on-delete;
            type uint32;
          }
          leaf shutdown {
            tailf:info
              "Administratively Enable/disable the interface";
            tailf:cli-boolean-no;
            default "false";
            type boolean;
          }
        }
        leaf level-capability {
          tailf:info
            "Specifies ISIS levels on the system";
          tailf:cli-no-value-on-delete;
          type enumeration {
            enum "level-1";
            enum "level-2";
            enum "level-1/2";
          }
        }
        container spf-wait {
          tailf:info
            "Configure ISIS SPF wait times";
          tailf:cli-embed-no-on-delete;
          tailf:cli-compact-syntax;
          tailf:cli-sequence-commands;
          leaf wait {
            tailf:cli-drop-node-name;
            tailf:cli-no-value-on-delete;
            type uint8 {
              range "1..120";
            }
          }
          leaf initial-wait {
            tailf:cli-drop-node-name;
            tailf:cli-no-value-on-delete;
            type uint32 {
              range "10..100000";
            }
          }
          leaf second-wait {
            tailf:cli-drop-node-name;
            tailf:cli-no-value-on-delete;
            type uint32 {
              range "1..100000";
            }
          }
        }
        leaf shutdown {
          tailf:info
            "Administratively enable or disable the operation of ISIS";
          tailf:cli-boolean-no;
          default "false";
          type boolean;
        }
      }
      list ospf {
        tailf:info
          "Create/Configure or delete OSPF instance";
        key "ospf-instance";
        leaf ospf-instance {
          type uint8 {
            range "0..31";
          }
        }
        leaf router-id {
          tailf:info
            "Configure router-id for OSPF";
          tailf:cli-drop-node-name;
          tailf:cli-no-value-on-delete;
          tailf:cli-hide-in-submode;
          default "0.0.0.0";
          type inet:ipv4-address;
        }
        leaf advertise-tunnel-link {
          tailf:info
            "Enable/disable advertisement of tunnel link";
          type empty;
        }
        list area {
          tailf:info
            "Configure an OSPF area";
          key "area-id";
          leaf area-id {
            type inet:ipv4-address;
          }
          container nssa {
            tailf:info
              "Configure an OSPF Not So Stubby Area (NSSA)";
            tailf:cli-add-mode;
            tailf:cli-embed-no-on-delete;
            leaf area-range {
              tailf:info
                "address ranges for route sum/suppression";
              tailf:cli-embed-no-on-delete;
              type empty;
            }
          }
          list interface {
            tailf:info
              "Configure OSPF on an IP interface";
            tailf:cli-embed-no-on-delete;
            tailf:cli-diff-dependency "/alu:router/interface/interface-name" {
              tailf:xpath-root 3;
              tailf:cli-trigger-on-all;
            }
            key "name";
            leaf name {
              tailf:non-strict-leafref {
                path "/ncs:devices/ncs:device/ncs:config/alu:router/interface/interface-name" {
                  tailf:xpath-root 3;
                }
              }
              type string;
            }
            leaf passive {
              tailf:info
                "Add/remove the passive property to/from the interface";
              tailf:cli-boolean-no;
              default "true";
              type boolean;
            }
            container message-digest-key {
              tailf:info
                "Configure a message digest key when MD5 authentication";
              tailf:cli-compact-syntax;
              tailf:cli-embed-no-on-delete;
              tailf:cli-break-sequence-commands;
              leaf key {
                tailf:cli-drop-node-name;
                type uint32;
              }
              leaf md5 {
                type empty;
              }
              leaf hash-value {
                tailf:cli-drop-node-name;
                type string;
              }
              leaf hash2 {
                type empty;
              }
            }
            leaf interface-type {
              tailf:info
                "Configure the interface type to be either broadcast or point-to-point";
              type enumeration {
                enum "broadcast";
                enum "point-to-point";
              }
            }
            leaf metric {
              tailf:info
                "Configure an explicit route cost metric for the interface";
              type uint32;
            }
            leaf authentication-type {
              tailf:info
                "Configure the authentication type to be used";
              tailf:cli-no-value-on-delete;
              type enumeration {
                enum "password";
                enum "message-digest";
              }
            }
            leaf bfd-enable {
              tailf:info
                "Enable BFD";
              type empty;
            }
            leaf shutdown {
              tailf:cli-boolean-no;
              default "false";
              type boolean;
            }
          }
        }
        leaf asbr {
          tailf:info
            "Configure the router as an ASBR (Autonomous System Boundary Router)";
          type empty;
        }
        leaf compatible-rfc1583 {
          tailf:info
            "Enable/disable OSPF summary and external route calculations in compliance with RFC1583 and earlier";
          type empty;
        }
        leaf disable-ldp-sync {
          tailf:info
            "Disable/Enable synchronization of IGP and LDP";
          type empty;
        }
        leaf-list export {
          tailf:info
            "Configure export route policies to determine which routes are exported from the route table";
          tailf:cli-no-value-on-delete;
          tailf:cli-flat-list-syntax;
          type string;
        }
        container export-limit {
          tailf:info
            "Maximum number of routes (prefixes) that can be exported into OSPF from the route table.";
          tailf:cli-compact-syntax;
          tailf:cli-sequence-commands;
          tailf:cli-embed-no-on-delete;
          leaf limit {
            tailf:cli-drop-node-name;
            tailf:cli-no-value-on-delete;
            type uint32;
          }
          leaf log {
            tailf:cli-no-name-on-delete;
            tailf:cli-no-value-on-delete;
            type uint8 {
              range "0..100";
            }
          }
        }
        container external-db-overflow {
          tailf:info
            "Limit on number of AS-external-LSAs in LSDB and wait time before processing these if limit is exceeded";
          tailf:cli-compact-syntax;
          tailf:cli-sequence-commands;
          tailf:cli-embed-no-on-delete;
          leaf limit {
            tailf:cli-drop-node-name;
            tailf:cli-no-value-on-delete;
            type int32 {
              range "-1..2147483647";
            }
          }
          leaf seconds {
            tailf:cli-drop-node-name;
            tailf:cli-no-value-on-delete;
            type uint32 {
              range "0..2147483647";
            }
          }
        }
        leaf external-preference {
          tailf:info
            "Preference for OSPF external routes";
          tailf:cli-no-value-on-delete;
          type uint8 {
            range "1..255";
          }
        }
        container graceful-restart {
          tailf:info
            "Enable/disable graceful-restart for OSPF";
          tailf:cli-add-mode;
          tailf:cli-embed-no-on-delete;
          leaf helper-disable {
            tailf:info
              "Enable/disable graceful restart helper mode for OSPF";
            tailf:cli-embed-no-on-delete;
            type empty;
          }
        }
        leaf ldp-over-rsvp {
          tailf:info
            "Allow ldp over rsvp processing in this OSPF instance";
          type empty;
        }
        leaf multicast-import {
          tailf:info
            "Enable/disable submission of routes into the multicast Route Table Manager by OSPF";
          type empty;
        }
        leaf overload {
          tailf:info
            "Configure the local router so that it appears to be overloaded";
          tailf:cli-no-value-on-delete;
          type uint16 {
            range "1..1800";
          }
        }
        leaf overload-include-stub {
          tailf:info
            "Enable/disable OSPF maximum metric usage for stub advertisement in case of overload";
          type empty;
        }
        container overload-on-boot {
          tailf:info
            "Configure the local router so that it appears to be overloaded at boot up";
          tailf:cli-embed-no-on-delete;
          tailf:cli-compact-syntax;
          presence "true";
          leaf timeout {
            tailf:cli-no-name-on-delete;
            tailf:cli-no-value-on-delete;
            type uint16 {
              range "1..1800";
            }
          }
        }
        leaf preference {
          tailf:info
            "Preference for OSPF internal routes";
          tailf:cli-no-value-on-delete;
          type uint8 {
            range "1..255";
          }
        }
        leaf reference-bandwidth {
          tailf:info
            "Reference bandwidth that provides a reference for the default costing of interfaces";
          tailf:cli-no-value-on-delete;
          type uint32 {
            range "1..100000000";
          }
        }
        leaf rsvp-shortcut {
          tailf:info
            "Enable/disable RSVP shortcut";
          type empty;
        }
        container timers {
          tailf:info
            "Configure OSPF timers";
          tailf:cli-embed-no-on-delete;
          tailf:cli-add-mode;
          leaf lsa-arrival {
            tailf:info
              "Configure the LSA arrival time";
            type uint16;
          }
          leaf lsa-generate {
            tailf:info
              "Configure the minimum delay that must pass between";
            type uint16;
          }
          leaf spf-wait {
            tailf:info
              "Configure the minimum delay that must pass between";
            type uint16;
          }
        }
        leaf traffic-engineering {
          tailf:info
            "Enable/disable traffic engineering route calculations";
          type empty;
        }
        leaf unicast-import-disable {
          tailf:info
            "Enable/disable submission of routes into the unicast Route Table Manager by OSPF";
          type empty;
        }
        leaf shutdown {
          tailf:info
            "Administratively enable/disable the OSPF instance";
          tailf:cli-boolean-no;
          default "false";
          type boolean;
        }
      }
      container ospf3 {
        tailf:info
          "Create/Configure or delete OSPF instance";
        tailf:cli-add-mode;
        presence "present";
        list area {
          key "area-id";
          leaf area-id {
            tailf:info
              "Configure an OSPF3 area";
            type union {
              type inet:ipv4-address;
              type uint32;
            }
          }
          list interface {
            tailf:info
              "Configure OSPF3 on an IP interface";
            key "interface-name";
            leaf interface-name {
              tailf:non-strict-leafref {
                path "/ncs:devices/ncs:device/ncs:config/alu:router/interface/interface-name" {
                  tailf:xpath-root 3;
                }
              }
              type string;
            }
            leaf interface-type {
              tailf:info
                "Configure the interface type to be either broadcast or point-to-point";
              tailf:cli-no-value-on-delete;
              type enumeration {
                enum "broadcast";
                enum "point-to-point";
              }
            }
            leaf passive {
              tailf:info
                "Add/remove the passive property to/from the interface";
              type empty;
            }
            leaf shutdown {
              tailf:info
                "Administratively enable/disable OSPF3 on the interface";
              tailf:cli-boolean-no;
              default "true";
              type boolean;
            }
          }
        }
        leaf shutdown {
          tailf:info
            "Administratively enable/disable the operation of OSPF3";
          tailf:cli-boolean-no;
          default "true";
          type boolean;
        }
      }
      container msdp {
        tailf:info
          "Create/Configure or delete MSDP instance";
        tailf:cli-add-mode;
        container local-address {
          tailf:info
            "Create/Configure or delete MSDP instance";
          tailf:cli-add-mode;
          leaf group {
            type empty;
          }
        }
      }
      container l2tp {
        tailf:info
          "Configure L2TP";
        tailf:cli-add-mode;
        tailf:cli-embed-no-on-delete;
        leaf shutdown {
          tailf:info
            "Administratively enable/disable the operation of L2TP";
          tailf:cli-boolean-no;
          default "false";
          type boolean;
        }
      }
      container ldp {
        tailf:info
          "Create/Configure or delete LDP instance";
        tailf:cli-add-mode;
        tailf:cli-embed-no-on-delete;
        presence "present";
        container aggregate-prefix-match {
          tailf:info
            "Enable/Disable aggregate prefix match procedures";
          tailf:cli-add-mode;
          tailf:cli-embed-no-on-delete;
          leaf shutdown {
            tailf:info
              "Administratively enable/disable LDP instance";
            tailf:cli-boolean-no;
            default "false";
            type boolean;
          }
        }
        container interface-parameters {
          tailf:info
            "Context to configure LDP interfaces and parameters";
          tailf:cli-recursive-delete;
          tailf:cli-add-mode;
          list interface {
            tailf:info
              "Configure LDP on an IP interface";
            tailf:cli-embed-no-on-delete;
            key "name";
            leaf name {
              tailf:non-strict-leafref {
                path "/ncs:devices/ncs:device/ncs:config/alu:router/interface/interface-name" {
                  tailf:xpath-root 3;
                }
              }
              type string;
            }
            leaf shutdown {
              tailf:cli-boolean-no;
              default "true";
              type boolean;
            }
          }
          container hello {
            tailf:info
              "Configure the hello timeout and factor";
            tailf:cli-embed-no-on-delete;
            tailf:cli-compact-syntax;
            tailf:cli-sequence-commands;
            leaf timeout {
              tailf:cli-drop-node-name;
              type uint16 {
                range "3..65535";
              }
            }
            leaf factor {
              tailf:cli-drop-node-name;
              type uint8 {
                range "1..255";
              }
            }
          }
        }
        leaf prefer-tunnel-in-tunnel {
          tailf:info
            "Configure preference of tunnel-in-tunnel over a simple LDP tunnel";
          type empty;
        }
        container targeted-session {
          tailf:info
            "Context to configure LDP targeted peers and parameters";
          tailf:cli-add-mode;
          leaf hello {
            tailf:info
              "Configure the hello timeout and factor for targeted LDP";
            tailf:cli-embed-no-on-delete;
            type empty;
          }
          list peer {
            tailf:info
              "Configure a targeted peer for LDP";
            tailf:cli-embed-no-on-delete;
            key "peer-address";
            leaf peer-address {
              type inet:ipv4-address;
            }
            leaf bfd-enable {
              tailf:info
                "Enable/Disable BFD tracking of LDP Session for the peer";
              tailf:cli-embed-no-on-delete;
              type empty;
            }
            container hello {
              tailf:info
                "Configure the hello timeout and factor for the peer";
              tailf:cli-embed-no-on-delete;
              tailf:cli-compact-syntax;
              tailf:cli-sequence-commands;
              leaf timeout {
                tailf:cli-drop-node-name;
                type uint16 {
                  range "3..65535";
                }
              }
              leaf factor {
                tailf:cli-drop-node-name;
                type uint8 {
                  range "1..255";
                }
              }
            }
            container keepalive {
              tailf:info
                "Configure the keepalive timeout and factor for the peer";
              tailf:cli-embed-no-on-delete;
              tailf:cli-compact-syntax;
              tailf:cli-sequence-commands;
              leaf timeout {
                tailf:cli-drop-node-name;
                type uint16 {
                  range "3..65535";
                }
              }
              leaf factor {
                tailf:cli-drop-node-name;
                type uint8 {
                  range "1..255";
                }
              }
            }
            leaf local-lsr-id {
              tailf:info
                "Configure local lsr-id";
              tailf:cli-embed-no-on-delete;
              type string {
                length "1..32";
              }
            }
            leaf shutdown {
              tailf:info
                "Administratively enable/disable the peer";
              tailf:cli-boolean-no;
              default "true";
              type boolean;
            }
          }
        }
        leaf label-withdrawal-delay {
          tailf:info
            "configure ldp label-withdrawal-delay";
          type uint32;
        }
        leaf shutdown {
          tailf:cli-boolean-no;
          default "false";
          type boolean;
        }
      }
      container dhcp {
        tailf:cli-add-mode;
        list local-dhcp-server {
          key "id";
          leaf id {
            type string;
          }
        }
      }
      list interface {
        tailf:cli-recursive-delete;
        tailf:cli-embed-no-on-delete;
        tailf:cli-diff-dependency "/alu:lag" {
          tailf:xpath-root 3;
        }
        tailf:cli-diff-dependency "/alu:port" {
          tailf:xpath-root 3;
        }
        key "interface-name";
        leaf interface-name {
          type string;
        }
        leaf address {
          tailf:cli-no-value-on-delete;
          type tailf:ipv4-address-and-prefix-length;
        }
        leaf description {
          tailf:cli-no-value-on-delete;
          type string;
        }
        leaf ldp-sync-time {
          type uint32;
        }
        leaf cpu-protection {
          type uint32;
        }
        leaf loopback {
          type empty;
        }
        leaf unnumbered-mpls-tp {
          tailf:cli-hide-in-submode;
          type empty;
        }
        leaf port {
          tailf:cli-no-value-on-delete;
          tailf:cli-diff-dependency "/alu:port/port-id" {
            tailf:xpath-root 3;
            tailf:cli-trigger-on-all;
          }
          tailf:non-strict-leafref {
            path "/ncs:devices/ncs:device/ncs:config/alu:port/port-id" {
              tailf:xpath-root 3;
            }
          }
          type string;
        }
        container icmp {
          tailf:cli-add-mode;
          container redirects {
            tailf:cli-compact-syntax;
            tailf:cli-sequence-commands {
              tailf:cli-reset-siblings;
            }
            leaf a {
              tailf:cli-drop-node-name;
              type uint32;
            }
            leaf b {
              tailf:cli-drop-node-name;
              type uint32;
            }
          }
          container unreachables {
            tailf:cli-compact-syntax;
            tailf:cli-sequence-commands {
              tailf:cli-reset-siblings;
            }
            leaf a {
              tailf:cli-drop-node-name;
              type uint32;
            }
            leaf b {
              tailf:cli-drop-node-name;
              type uint32;
            }
          }
          container ttl-expired {
            tailf:cli-compact-syntax;
            tailf:cli-sequence-commands {
              tailf:cli-reset-siblings;
            }
            leaf a {
              tailf:cli-drop-node-name;
              type uint32;
            }
            leaf b {
              tailf:cli-drop-node-name;
              type uint32;
            }
          }
        }
        leaf qos {
          tailf:cli-no-value-on-delete;
          tailf:cli-diff-dependency "/alu:qos/network/id" {
            tailf:xpath-root 3;
            tailf:cli-trigger-on-all;
          }
          tailf:non-strict-leafref {
            path "/ncs:devices/ncs:device/ncs:config/alu:qos/network/id" {
              tailf:xpath-root 3;
            }
          }
          type uint16;
        }
        container ipv6 {
          tailf:cli-add-mode;
          list address {
            tailf:cli-embed-no-on-delete;
            tailf:cli-suppress-mode;
            key "addr";
            leaf addr {
              type tailf:ipv6-address-and-prefix-length;
            }
            leaf eui-64 {
              tailf:cli-hide-in-submode;
              type empty;
            }
            leaf preferred {
              tailf:cli-hide-in-submode;
              type empty;
            }
          }
          container bfd {
            tailf:cli-embed-no-on-delete;
            tailf:cli-compact-syntax;
            tailf:cli-sequence-commands;
            leaf id {
              tailf:cli-drop-node-name;
              tailf:cli-no-value-on-delete;
              type uint32;
            }
            leaf receive {
              tailf:cli-no-name-on-delete;
              tailf:cli-no-value-on-delete;
              type uint32;
            }
            leaf multiplier {
              tailf:cli-no-name-on-delete;
              tailf:cli-no-value-on-delete;
              type uint32;
            }
            leaf type {
              tailf:cli-no-name-on-delete;
              tailf:cli-no-value-on-delete;
              type enumeration {
                enum "cpm-np";
              }
            }
          }
        }
        container bfd {
          tailf:info
            "Configure BFD parameters";
          tailf:cli-embed-no-on-delete;
          tailf:cli-compact-syntax;
          tailf:cli-sequence-commands;
          leaf id {
            tailf:cli-drop-node-name;
            tailf:cli-no-value-on-delete;
            type uint32;
          }
          leaf receive {
            tailf:cli-no-name-on-delete;
            tailf:cli-no-value-on-delete;
            type uint32;
          }
          leaf multiplier {
            tailf:cli-no-name-on-delete;
            tailf:cli-no-value-on-delete;
            type uint32;
          }
          leaf type {
            tailf:cli-no-name-on-delete;
            tailf:cli-no-value-on-delete;
            type enumeration {
              enum "cpm-np";
            }
          }
        }
        leaf autonomous-system {
          tailf:cli-no-value-on-delete;
          type uint16;
        }
        leaf shutdown {
          tailf:cli-boolean-no;
          default "false";
          type boolean;
        }
      }
      container mpls {
        tailf:info
          "Create/Configure or delete MPLS instance";
        tailf:cli-embed-no-on-delete;
        tailf:cli-recursive-delete;
        tailf:cli-add-mode;
        tailf:callpoint mpls-hook {
          tailf:set-hook node;
        }
        presence "true";
        leaf resignal-timer {
          tailf:info
            "Configure the resignal timer for the MPLS instance";
          tailf:cli-no-value-on-delete;
          type uint16 {
            range "30..10080";
          }
        }
        container srlg-frr {
          tailf:info
            "Enable/disable SRLG for FRR path computation";
          tailf:cli-compact-syntax;
          presence "present";
          leaf strict {
            tailf:cli-no-name-on-delete;
            type empty;
          }
        }
        list interface {
          tailf:info
            "Configure MPLS on an IP interface";
          tailf:cli-embed-no-on-delete;
          key "name";
          leaf name {
            tailf:non-strict-leafref {
              path "/ncs:devices/ncs:device/ncs:config/alu:router/interface/interface-name" {
                tailf:xpath-root 3;
              }
            }
            type string;
          }
          leaf shutdown {
            tailf:info
              "Administratively enable/disable MPLS on the interface";
            tailf:cli-boolean-no;
            default "false";
            type boolean;
          }
        }
        list path {
          tailf:info
            "Configure the path to be used for a LSP";
          tailf:cli-embed-no-on-delete;
          key "name";
          leaf name {
            type string;
          }
          leaf shutdown {
            tailf:info
              "Administratively enable/disable the LSP path";
            tailf:cli-embed-no-on-delete;
            tailf:cli-boolean-no;
            default "true";
            type boolean;
          }
        }
        list lsp-template {
          tailf:info
            "Creates an LSP Template that will be referenced";
          tailf:cli-embed-no-on-delete;
          key "template";
          leaf template {
            tailf:cli-hide-in-submode;
            type string;
          }
          leaf p2mp {
            tailf:cli-hide-in-submode;
            type empty;
          }
          leaf default-path {
            tailf:info
              "Specify default path to be used for signaling LSP";
            tailf:cli-embed-no-on-delete;
            type string;
          }
          container fast-reroute {
            tailf:info
              "Configure fast reroute for LSP";
            tailf:cli-add-mode;
            tailf:cli-embed-no-on-delete;
            leaf frr-method {
              tailf:info
                "<frr-method>;;one-to-one|facility";
              tailf:cli-hide-in-submode;
              tailf:cli-drop-node-name;
              type enumeration {
                enum "facility";
                enum "one-to-one";
              }
            }
            leaf hop-limit {
              tailf:info
                "Configure hop limit  for fast reroute";
              tailf:cli-embed-no-on-delete;
              type empty;
            }
          }
          leaf shutdown {
            tailf:info
              "Administratively enable/disable the LSP Template";
            tailf:cli-boolean-no;
            default "true";
            type boolean;
          }
        }
        list lsp {
          tailf:info
            "Creates an LSP that will be signaled dynamically";
          tailf:cli-embed-no-on-delete;
          tailf:cli-compact-syntax;
          key "name";
          leaf name {
            type string;
          }
          leaf bypass-only {
            tailf:cli-hide-in-submode;
            tailf:cli-no-name-on-delete;
            type empty;
          }
          leaf p2mp-lsp {
            tailf:cli-hide-in-submode;
            tailf:cli-no-name-on-delete;
            type empty;
          }
          leaf mpls-tp {
            tailf:cli-hide-in-submode;
            tailf:cli-no-name-on-delete;
            tailf:cli-no-value-on-delete;
            type uint16 {
              range "1..61440";
            }
          }
          leaf to {
            tailf:info
              "IP address of the egress router for the LSP";
            type inet:ipv4-address;
          }
          container fast-reroute {
            tailf:info
              "Configure fast reroute for LSP";
            tailf:cli-add-mode;
            tailf:cli-embed-no-on-delete;
            leaf frr-method {
              tailf:info
                "<frr-method>;;one-to-one|facility";
              tailf:cli-hide-in-submode;
              tailf:cli-drop-node-name;
              type enumeration {
                enum "facility";
                enum "one-to-one";
              }
            }
            leaf hop-limit {
              tailf:info
                "Configure hop limit  for fast reroute";
              tailf:cli-embed-no-on-delete;
              type empty;
            }
            leaf node-protect {
              tailf:info
                "Configure node protect";
              tailf:cli-embed-no-on-delete;
              type empty;
            }
          }
          container primary {
            tailf:info
              "Configure a preferred path for the LSP";
            tailf:cli-add-mode;
            tailf:cli-embed-no-on-delete;
            leaf path {
              tailf:cli-drop-node-name;
              tailf:cli-hide-in-submode;
              tailf:non-strict-leafref {
                path "/ncs:devices/ncs:device/ncs:config/alu:router/mpls/path/name" {
                  tailf:xpath-root 3;
                }
              }
              type string;
            }
            leaf adaptive {
              tailf:info
                "Enable/Disable make-before-break functionality";
              tailf:cli-embed-no-on-delete;
              type empty;
            }
          }
          container secondary {
            tailf:cli-add-mode;
            leaf path {
              tailf:cli-drop-node-name;
              tailf:cli-hide-in-submode;
              tailf:non-strict-leafref {
                path "/ncs:devices/ncs:device/ncs:config/alu:router/mpls/path/name" {
                  tailf:xpath-root 3;
                }
              }
              type string;
            }
            leaf adaptive {
              tailf:cli-embed-no-on-delete;
              type empty;
            }
          }
          leaf cspf {
            tailf:info
              "Enable/disable CSPF support for the LSP";
            tailf:cli-embed-no-on-delete;
            type empty;
          }
          leaf shutdown {
            tailf:info
              "Administratively enable/disable the LSP";
            tailf:cli-show-no;
            type empty;
          }
        }
        list static-lsp {
          tailf:info
            "Configure a static LSP on the ingress router";
          tailf:cli-embed-no-on-delete;
          key "name";
          leaf name {
            type string;
          }
          container push {
            tailf:info
              "Label to be pushed on the label stack and the next hop IP address";
            tailf:cli-compact-syntax;
            tailf:cli-sequence-commands;
            leaf label {
              tailf:cli-drop-node-name;
              type union {
                type uint32 {
                  range "16..1048575";
                }
                type enumeration {
                  enum "implicit-null-label";
                }
              }
            }
            leaf nexthop {
              type inet:ipv4-address;
            }
          }
          leaf to {
            tailf:info
              "IP address of the egress router for the static LSP";
            tailf:cli-no-name-on-delete;
            tailf:cli-no-value-on-delete;
            type inet:ipv4-address;
          }
          leaf shutdown {
            tailf:info
              "Administratively enable/disable the static LSP";
            tailf:cli-boolean-no;
            default "true";
            type boolean;
          }
        }
        leaf shutdown {
          tailf:info
            "Administratively enable/disable the MPLS instance";
          tailf:cli-boolean-no;
          default "true";
          type boolean;
        }
      }
      container rsvp {
        tailf:info
          "Create/Configure or delete RSVP instance";
        tailf:cli-embed-no-on-delete;
        tailf:cli-recursive-delete;
        tailf:cli-add-mode;
        tailf:cli-diff-dependency "../mpls" {
          tailf:xpath-root 3;
        }
        must '../mpls' {
          tailf:xpath-root 3;
        }
        presence "present";
        list interface {
          tailf:info
            "Configure RSVP on an IP interface";
          tailf:cli-embed-no-on-delete;
          tailf:cli-diff-dependency "/alu:router/mpls/interface/name" {
            tailf:xpath-root 3;
          }
          key "name";
          leaf name {
            tailf:non-strict-leafref {
              path "/ncs:devices/ncs:device/ncs:config/alu:router/interface/interface-name" {
                tailf:xpath-root 3;
              }
            }
            type string;
          }
          container refresh-reduction {
            tailf:info
              "Enable/Disable RSVP overhead refresh reduction";
            tailf:cli-embed-no-on-delete;
            tailf:cli-add-mode;
            leaf reliable-delivery {
              tailf:info
                "Enable/Disable reliable delivery of RSVP messages";
              tailf:cli-embed-no-on-delete;
              type empty;
            }
          }
          container authentication-key {
            tailf:info
              "Configure the RSVP authentication key for all peers";
            tailf:cli-embed-no-on-delete;
            tailf:cli-compact-syntax;
            tailf:cli-sequence-commands;
            leaf key {
              tailf:cli-drop-node-name;
              tailf:cli-no-value-on-delete;
              type string;
            }
            leaf type {
              tailf:cli-drop-node-name;
              tailf:cli-no-value-on-delete;
              type enumeration {
                enum "hash";
                enum "hash2";
              }
            }
          }
          leaf shutdown {
            tailf:info
              "Administratively enable/disable RSVP on the interface";
            tailf:cli-boolean-no;
            default "false";
            type boolean;
          }
        }
        leaf shutdown {
          tailf:info
            "Administratively enable/disable the RSVP instance";
          tailf:cli-boolean-no;
          default "true";
          type boolean;
        }
      }
      container router-advertisement {
        tailf:cli-add-mode;
        tailf:cli-diff-dependency "/alu:service/ies" {
          tailf:xpath-root 3;
        }
        list interface {
          tailf:info
            "Configure router advertisement properties on an interface";
          tailf:cli-embed-no-on-delete;
          key "ip-int-name";
          leaf ip-int-name {
            type string;
            tailf:non-strict-leafref {
              path "/ncs:devices/ncs:device/ncs:config/alu:router/interface/interface-name" {
                tailf:xpath-root 3;
              }
            }
          }
          leaf current-hop-limit {
            tailf:info
              "Configure the router to advertise the hop-limit";
            tailf:cli-no-value-on-delete;
            type uint8;
          }
          leaf max-advertisement-interval {
            tailf:info
              "Configure max interval between sending ICMPv6";
            tailf:cli-no-value-on-delete;
            type uint16 {
              range "4..1800";
            }
          }
          leaf min-advertisement-interval {
            tailf:info
              "Configure min interval between sending ICMPv6";
            tailf:cli-no-value-on-delete;
            type uint16 {
              range "3..1350";
            }
          }
          leaf mtu {
            tailf:info
              "Configure the MTU for sending packets to the router";
            tailf:cli-no-value-on-delete;
            type uint16 {
              range "1280..9212";
            }
          }
          leaf managed-configuration {
            tailf:info
              "Configure the managed-config-flag to be advertised";
            type empty;
          }
          leaf other-stateful-configuration {
            tailf:info
              "Configure the other-config-flag to be advertised";
            type empty;
          }
          list prefix {
            tailf:info
              "Configure prefix that needs to be included";
            tailf:cli-embed-no-on-delete;
            key "ipv6-prefix";
            leaf ipv6-prefix {
              type inet:ipv6-prefix;
            }
          }
          leaf reachable-time {
            tailf:info
              "Configure how long this router should be reachable";
            tailf:cli-no-value-on-delete;
            type uint32 {
              range "0..3600000";
            }
          }
          leaf retransmit-time {
            tailf:info
              "Configure the time interval to be advertised";
            tailf:cli-no-value-on-delete;
            type uint32 {
              range "0..1800000";
            }
          }
          leaf router-lifetime {
            tailf:info
              "Configure the lifetime value that the router advertises";
            tailf:cli-no-value-on-delete;
            type uint16 {
              range "0..9000";
            }
          }
          leaf use-virtual-mac {
            tailf:info
              "Send Router Advertisement messages using VRRP";
            type empty;
          }
          leaf shutdown {
            tailf:info
              "Command to disable router advertisement on an interface";
            tailf:cli-boolean-no;
            default "true";
            type boolean;
          }
        }
      }
      container mld {
        tailf:cli-add-mode;
        tailf:cli-diff-dependency "/alu:service/ies" {
          tailf:xpath-root 3;
        }
        list interface {
          tailf:cli-embed-no-on-delete;
          key "ip-int-name";
          leaf ip-int-name {
            type string;
            tailf:non-strict-leafref {
              path "/ncs:devices/ncs:device/ncs:config/alu:router/interface/interface-name" {
                tailf:xpath-root 3;
              }
            }
          }
          leaf shutdown {
            tailf:cli-boolean-no;
            default "true";
            type boolean;
          }
        }
        leaf shutdown {
          tailf:cli-boolean-no;
          default "true";
          type boolean;
        }
      }
      container policy-options {
        tailf:cli-embed-no-on-delete;
        tailf:cli-recursive-delete;
        tailf:cli-explicit-exit;
        tailf:cli-add-mode;
        container begin {
          tailf:info
            "Switch to edit mode for route policies";
          tailf:cli-add-mode;
          tailf:cli-exit-command "commit";
          tailf:cli-recursive-delete;
          list prefix-list {
            tailf:cli-embed-no-on-delete;
            key "name";
            leaf name {
              type string;
            }
            list prefix {
              tailf:cli-suppress-mode;
              tailf:cli-compact-syntax;
              tailf:cli-embed-no-on-delete;
              key "ip-prefix";
              leaf ip-prefix {
                type union {
                  type tailf:ipv4-address-and-prefix-length;
                  type tailf:ipv6-address-and-prefix-length;
                }
              }
              choice a {
                leaf exact {
                  type empty;
                }
                leaf longer {
                  type empty;
                }
                leaf through {
                  type uint8 {
                    range "0..128";
                  }
                }
                leaf prefix-length-range {
                  type string;
                }
              }
            }
          }
          list community {
            tailf:info
              "Create/delete a community list for use in route policy entries";
            tailf:cli-compact-syntax;
            tailf:cli-suppress-mode;
            key "name";
            leaf name {
              type string;
            }
            choice community-choice {
              case a {
                leaf-list members {
                  tailf:cli-flat-list-syntax;
                  tailf:cli-no-name-on-delete;
                  tailf:cli-no-value-on-delete;
                  type string {
                    length "1..72";
                  }
                }
              }
              case b {
                leaf expression {
                  type string {
                    length "1..900";
                  }
                }
              }
            }
          }
          list damping {
            tailf:info
              "Configure a damping profile for use in route policy entries";
            tailf:cli-embed-no-on-delete;
            key "name";
            leaf name {
              type string {
                length "1..32";
              }
            }
            leaf half-life {
              tailf:info
                "The time in minutes after which the accumulated figure-of-merit value is reduced by half if the route remains stable.";
              tailf:cli-no-value-on-delete;
              type uint8 {
                range "1..45";
              }
            }
            leaf max-suppress {
              tailf:info
                "The maximum time in minutes that a route can be suppressed no matter how unstable it has been.";
              tailf:cli-no-value-on-delete;
              type uint16 {
                range "1..720";
              }
            }
            leaf reuse {
              tailf:info
                "The figure-of-merit value below which a suppressed
                 route can be used again.";
              tailf:cli-no-value-on-delete;
              type uint32 {
                range "1..20000";
              }
            }
            leaf suppress {
              tailf:info
                "The figure-of-merit value above which a route is suppressed for use or inclusion in route advertisements.";
              tailf:cli-no-value-on-delete;
              type uint32 {
                range "1..20000";
              }
            }
          }
          list policy-statement {
            tailf:info
              "Configuring a route policy statement";
            tailf:cli-embed-no-on-delete;
            tailf:cli-recursive-delete;
            key "name";
            leaf name {
              type string;
            }
            container default-action {
              tailf:info
                "Configuring actions for routes that do not match any policy entries";
              uses policy-options-action-grouping;
            }
            list entry {
              tailf:info
                "Configure a route policy entry within the policy statement";
              tailf:cli-embed-no-on-delete;
              key "id";
              leaf id {
                type uint32 {
                  range "1..4294967295";
                }
              }
              leaf description {
                tailf:info
                  "Textual description for the policy statement";
                tailf:cli-embed-no-on-delete;
                tailf:cli-no-value-on-delete;
                type string {
                  length "1..80";
                }
              }
              container action {
                tailf:info
                  "Configure actions to take for routes matching a policy entry";
                uses policy-options-action-grouping;
              }
              container from {
                tailf:info
                  "Configure policy match criteria based on source of routes or protocol from which it is received";
                tailf:cli-embed-no-on-delete;
                tailf:cli-add-mode;
                leaf area {
                  tailf:info
                    "Configure an OSPF area as a match criterion for the entry";
                  tailf:cli-no-value-on-delete;
                  type union {
                    type inet:ipv4-address;
                    type uint32 {
                      range "0..4294967295";
                    }
                  }
                }
                leaf as-path {
                  tailf:info
                    "Configures an AS Path regular expression statement as a match criterion for the entry";
                  tailf:cli-no-value-on-delete;
                  type string {
                    length "1..32";
                  }
                }
                leaf as-path-group {
                  tailf:info
                    "Configures an AS Path Group as a match criterion for the entry";
                  tailf:cli-no-value-on-delete;
                  type string {
                    length "1..32";
                  }
                }
                leaf community {
                  tailf:info
                    "Configure a community list as a match criterion for the entry";
                  tailf:cli-no-value-on-delete;
                  type string {
                    length "1..32";
                  }
                }
                leaf external {
                  tailf:info
                    "Configure external ISIS route matching criterion for the entry";
                  type empty;
                }
                leaf-list family {
                  tailf:info
                    "Configure the address families that this condition would match against";
                  tailf:cli-no-value-on-delete;
                  tailf:cli-flat-list-syntax;
                  type enumeration {
                    enum "ipv4";
                    enum "ipv6";
                    enum "mcast-ipv4";
                    enum "mcast-ipv6";
                    enum "vpn-ipv4";
                    enum "vpn-ipv6";
                    enum "l2-vpn";
                    enum "mvpn-ipv4";
                    enum "flow-ipv4";
                    enum "ms-pw";
                    enum "mdt-safi";
                    enum "route-target";
                    enum "mcast-vpn-ipv4";
                    enum "mvpn-ipv6";
                    enum "flow-ipv6";
                  }
                }
                leaf group-address {
                  tailf:info
                    "Configure a prefix list of multicast group address as a match criterion for the entry";
                  tailf:cli-no-value-on-delete;
                  type string {
                    length "1..32";
                  }
                }
                leaf host-ip {
                  tailf:info
                    "Configure a prefix list of IGMP host ip address as a match criterion for this entry";
                  tailf:cli-no-value-on-delete;
                  type string {
                    length "1..32";
                  }
                }
                leaf interface {
                  tailf:info
                    "Configure the name of the interface as a match criterion for this entry";
                  tailf:cli-no-value-on-delete;
                  type string {
                    length "1..32";
                  }
                }
                leaf level {
                  tailf:info
                    "Configure ISIS route level as a match criterion for the entry";
                  tailf:cli-no-value-on-delete;
                  type uint8 {
                    range "1..2";
                  }
                }
                container neighbor {
                  tailf:info
                    "Configure a neighbor or prefix list as match criterion for the entry";
                  tailf:cli-embed-no-on-delete;
                  choice a {
                    leaf ip-address {
                      tailf:cli-drop-node-name;
                      tailf:cli-no-value-on-delete;
                      type inet:ipv4-address;
                    }
                    leaf prefix-list {
                      tailf:cli-no-name-on-delete;
                      tailf:cli-no-value-on-delete;
                      type string;
                    }
                  }
                }
                leaf origin {
                  tailf:info
                    "Configure a BGP or Subscriber Management origin attribute as a match criterion for the entry";
                  tailf:cli-no-value-on-delete;
                  type enumeration {
                    enum "igp";
                    enum "egp";
                    enum "incomplete";
                    enum "any";
                    enum "aaa";
                    enum "dhcp";
                    enum "ludb";
                  }
                }
                leaf policy {
                  tailf:info
                    "Configures a policy statement as a match criterion for the entry";
                  tailf:cli-no-value-on-delete;
                  type string {
                    length "1..32";
                  }
                }
                leaf-list prefix-list {
                  tailf:info
                    "Configure a prefix list as a match criterion for the entry";
                  tailf:cli-flat-list-syntax;
                  type string {
                    length "1..32";
                  }
                }
                leaf protocol {
                  tailf:info
                    "Configure a routing protocol as a match criterion for the entry";
                  tailf:cli-no-value-on-delete;
                  type enumeration {
                    enum "direct";
                    enum "static";
                    enum "bgp";
                    enum "isis";
                    enum "ospf";
                    enum "rip";
                    enum "aggregate";
                    enum "bgp-vpn";
                    enum "igmp";
                    enum "pim";
                    enum "ospf3";
                    enum "ldp";
                    enum "sub-mgmt";
                    enum "mld";
                    enum "managed";
                    enum "vpn-leak";
                    enum "tms";
                    enum "nat";
                    enum "periodic";
                    enum "ipsec";
                    enum "mpls";
                    enum "dhcpv6-pd";
                    enum "dhcpv6-na";
                    enum "dhcpv6-ta";
                    enum "dhcpv6-pd-excl";
                  }
                }
                leaf source-address {
                  tailf:info
                    "Configure a multicast data source address as a match criterion for this entry";
                  tailf:cli-no-value-on-delete;
                  type union {
                    type inet:ipv4-address;
                    type inet:ipv6-address;
                  }
                }
                leaf state {
                  tailf:info
                    "Configure a state as a match criterion for the entry";
                  tailf:cli-no-value-on-delete;
                  type enumeration {
                    enum "srrp-master";
                    enum "srrp-non-master";
                    enum "ipsec-master-with-peer";
                    enum "ipsec-non-master";
                    enum "ipsec-master-without-peer";
                  }
                }
                leaf tag {
                  tailf:info
                    "Configure a route tag as a match criterionfor the entry";
                  tailf:cli-no-value-on-delete;
                  type uint32;
                }
                leaf type {
                  tailf:info
                    "Configure an OSPF type metric as a match criterionfor the entry";
                  tailf:cli-no-value-on-delete;
                  type uint8 {
                    range "1..2";
                  }
                }
              }
              container to {
                tailf:info
                  "Configure policy match criteria based on destination of routes or protocol into which it is advertised";
                tailf:cli-embed-no-on-delete;
                tailf:cli-add-mode;
                leaf level {
                  tailf:info
                    "Configure ISIS route level as a match criterion for the entry";
                  tailf:cli-no-value-on-delete;
                  type uint8 {
                    range "1..2";
                  }
                }
                leaf neighbor {
                  tailf:info
                    "Configure a neighbor or prefix list as matchcriterion for the entry";
                  tailf:cli-no-value-on-delete;
                  type union {
                    type inet:ipv4-address;
                    type inet:ipv6-address;
                    type string {
                      length "1..32";
                    }
                  }
                }
                leaf-list prefix-list {
                  tailf:info
                    "Configure a prefix list as a match criterion for the entry";
                  tailf:cli-flat-list-syntax;
                  type string {
                    length "1..32";
                  }
                }
                leaf protocol {
                  tailf:info
                    "Configure a routing protocol as a match criterion for the entry";
                  tailf:cli-no-value-on-delete;
                  type enumeration {
                    enum "direct";
                    enum "static";
                    enum "bgp";
                    enum "isis";
                    enum "ospf";
                    enum "rip";
                    enum "aggregate";
                    enum "bgp-vpn";
                    enum "igmp";
                    enum "pim";
                    enum "ospf3";
                    enum "ldp";
                    enum "sub-mgmt";
                    enum "mld";
                    enum "managed";
                    enum "vpn-leak";
                    enum "tms";
                    enum "nat";
                    enum "periodic";
                    enum "ipsec";
                    enum "mpls";
                    enum "dhcpv6-pd";
                    enum "dhcpv6-na";
                    enum "dhcpv6-ta";
                    enum "dhcpv6-pd-excl";
                  }
                }
              }
            }
          }
          list as-path {
            tailf:info
              "Create/delete AS Path regular expressions for use in route policy entries";
            tailf:cli-compact-syntax;
            key "name";
            leaf name {
              type string;
            }
            leaf regexp {
              tailf:cli-drop-node-name;
              type string;
            }
          }
        }
      }
      container pim {
        tailf:info
          "Create/Configure or delete PIM instance";
        tailf:cli-add-mode;
        presence "present";
        list interface {
          tailf:info
            "Configure PIM interface";
          key "ip-int-name";
          leaf ip-int-name {
            type leafref {
              path "/ncs:devices/ncs:device/ncs:config/alu:router/interface/interface-name" {
                tailf:xpath-root 3;
              }
            }
          }
          leaf assert-period {
            tailf:info
              "Configure the period for periodic refreshes of PIM Assert messages on an interface";
            tailf:cli-no-value-on-delete;
            type uint16 {
              range "1..300";
            }
          }
          leaf bfd-enable {
            tailf:info
              "Enable BFD";
            type enumeration {
              enum "ipv4";
              enum "ipv6";
            }
          }
          leaf bsm-check-rtr-alert {
            tailf:info
              "Enable/disable accepting of BSM packets without router alert option";
            type empty;
          }
          leaf hello-interval {
            tailf:info
              "Configure the frequency at which PIM hello messages are sent over this interface";
            tailf:cli-no-value-on-delete;
            type uint8;
          }
          leaf hello-multiplier {
            tailf:info
              "Configure hello-multiplier in multiples of 0.1 (deci-units)";
            tailf:cli-no-value-on-delete;
            type uint8 {
              range "20..100";
            }
          }
          leaf improved-assert {
            tailf:info
              "Enable/disable improved assert processing";
            type empty;
          }
          leaf instant-prune-echo {
            tailf:info
              "Enable/Disable instant PruneEcho for a PIM interface";
            type empty;
          }
          leaf ipv4-multicast-disable {
            tailf:info
              "Administratively disable/enable PIM operation for IPv4 on this interface";
            type empty;
          }
          leaf ipv6-multicast-disable {
            tailf:info
              "Administratively disable/enable PIM operation for IPv6 on this interface";
            type empty;
          }
          leaf max-groups {
            tailf:info
              "Configure the maximum number of groups for this interface";
            tailf:cli-no-value-on-delete;
            type uint16 {
              range "1..16000";
            }
          }
          container mcac {
            tailf:info
              "Configure multicast CAC policy and constraints for this interface";
            tailf:cli-add-mode;
            container mc-constraints {
              tailf:info
                "Create context that allows for the configuration of the different levels and their associated bandwidth for multicast cac policy on this interface";
              tailf:cli-add-mode;
              container level {
                tailf:info
                  "Configure levels and their associated bandwidth for multicast cac policy on this interface";
                tailf:cli-embed-no-on-delete;
                tailf:cli-sequence-commands;
                leaf level-id {
                  tailf:cli-drop-node-name;
                  tailf:cli-no-value-on-delete;
                  type uint8 {
                    range "1..8";
                  }
                }
                leaf bw {
                  tailf:cli-optional-in-sequence;
                  tailf:cli-no-name-on-delete;
                  tailf:cli-no-value-on-delete;
                  type enumeration {
                    enum "kbps";
                  }
                }
              }
              list number-down {
                tailf:info
                  "Configure number of ports down along with level for multicast cac policy on this interface";
                tailf:cli-suppress-mode;
                key "number-lag-port-down";
                leaf number-lag-port-down {
                  type uint8 {
                    range "1..64";
                  }
                }
                leaf level-id {
                  tailf:cli-drop-node-name;
                  tailf:cli-no-value-on-delete;
                  type uint8 {
                    range "1..8";
                  }
                }
              }
              leaf use-lag-port-weight {
                tailf:info
                  "Enable/disable using the LAG port weight while calculating Multicast CAC constraints";
                type empty;
              }
              leaf shutdown {
                tailf:info
                  "Administratively enable/disable constraint for multicast cac policy";
                tailf:cli-boolean-no;
                default "true";
                type boolean;
              }
            }
            leaf policy {
              tailf:info
                "Configure multicast CAC policy name";
              tailf:cli-no-value-on-delete;
              type string {
                length "1..32";
              }
            }
            container unconstrained-bw {
              tailf:info
                "Configure unconstrained-bw for multicast cac policy on this interface";
              tailf:cli-embed-no-on-delete;
              tailf:cli-sequence-commands;
              leaf bandwidth {
                tailf:cli-drop-node-name;
                tailf:cli-no-value-on-delete;
                type uint32 {
                  range "0..2147483647";
                }
              }
              leaf mandatory-bw {
                tailf:cli-no-name-on-delete;
                tailf:cli-no-value-on-delete;
                type uint32 {
                  range "0..2147483647";
                }
              }
            }
          }
          leaf multicast-senders {
            tailf:info
              "Configure the way subnet matching is done for incoming data packets on this interface";
            tailf:cli-no-value-on-delete;
            type enumeration {
              enum "auto";
              enum "always";
              enum "never";
            }
          }
          leaf p2mp-ldp-tree-join {
            tailf:info
              "Enable/Disable p2mp-ldp-tree-join";
            type enumeration {
              enum "ipv4";
              enum "ipv6";
            }
          }
          leaf priority {
            tailf:info
              "Configure the DR election priority for this interface";
            tailf:cli-no-value-on-delete;
            type uint32;
          }
          container sticky-dr {
            tailf:info
              "Enable/disable sticky-DR and configure DR priority for sticky-DR";
            tailf:cli-embed-no-on-delete;
            leaf priority {
              tailf:cli-no-name-on-delete;
              tailf:cli-no-value-on-delete;
              type uint32;
            }
            leaf three-way-hello {
              tailf:info
                "Configure compatibility mode for three-way-hello";
              type empty;
            }
            leaf tracking-support {
              tailf:info
                "Enable/disable tracking support";
              type empty;
            }
          }
          leaf shutdown {
            tailf:info
              "Administratively enable/disable the interface";
            tailf:cli-boolean-no;
            default "true";
            type boolean;
          }
        }
        leaf ipv4-multicast-disable {
          tailf:info
            "Administratively disable/enable PIM operation for IPv4";
          type empty;
        }
        leaf ipv6-multicast-disable {
          tailf:info
            "Administratively disable/enable PIM operation for IPv6";
          type empty;
        }
        container rp {
          tailf:info
            "Configure the router as static or Candidate-RP";
          tailf:cli-add-mode;
          list anycast {
            tailf:info
              "Configure PIM anycast protocol instance for the RP";
            key "rp-ip-address";
            leaf rp-ip-address {
              type inet:ipv4-address;
            }
            list rp-set-peer {
              tailf:cli-suppress-mode;
              tailf:info
                "Configure a peer in the anycast rp-set";
              key "ip-address";
              leaf ip-address {
                tailf:cli-drop-node-name;
                type inet:ipv4-address;
              }
            }
          }
          container static {
            tailf:info
              "Context to configure static group to RP mapping";
            tailf:cli-add-mode;
            presence "true";
            list address {
              tailf:info
                "Configure the RP address for multicast group prefixes";
              key "ip-address";
              leaf ip-address {
                tailf:cli-drop-node-name;
                type union {
                  type inet:ipv4-address;
                  type inet:ipv6-address;
                }
              }
              list group-prefix {
                tailf:cli-suppress-mode;
                tailf:info
                  "Configure a group prefix for the RP address";
                key "grp-ip-addr";
                leaf grp-ip-addr {
                  tailf:cli-drop-node-name;
                  type tailf:ipv4-address-and-prefix-length;
                }
              }
            }
          }
          container bsr-candidate {
            tailf:info
              "Context to configure Candidate Bootstrap parameters";
            tailf:cli-add-mode;
            leaf shutdown {
              tailf:info
                "Administratively enable/disable participation of the router in bootstrap election";
              tailf:cli-boolean-no;
              default "true";
              type boolean;
            }
          }
          container rp-candidate {
            tailf:info
              "Context to configure the Candidate RP parameters";
            tailf:cli-add-mode;
            leaf shutdown {
              tailf:info
                "Administratively enable/disable the Candidate-RP";
              tailf:cli-boolean-no;
              default "true";
              type boolean;
            }
          }
        }
        leaf shutdown {
          tailf:info
            "Administratively enable or disable the operation of PIM";
          tailf:cli-boolean-no;
          default "false";
          type boolean;
        }
      }
    }
    container system {
      tailf:ncs-device-type "cli-ned";
      tailf:display-when "not(../../ncs:module) or ../../ncs:module[ncs:name='tailf-ned-alu-sr']";
      tailf:info
        "Configure system parameters";
      tailf:cli-recursive-delete;
      tailf:cli-add-mode;
      container alarms {
        leaf max-cleared {
          type string;
        }
        leaf shutdown {
          tailf:cli-boolean-no;
          default "true";
          type boolean;
        }
      }
      container atm {
        leaf atm-location-id {
          type string;
        }
        container oam {
          leaf loopback-period {
            type string;
          }
          leaf retry-down {
            type string;
          }
          leaf retry-up {
            type string;
          }
        }
      }
      leaf boot-bad-exec {
        type string;
      }
      leaf boot-good-exec {
        type string;
      }
      list chassis-mode {
        tailf:cli-recursive-delete;
        tailf:cli-embed-no-on-delete;
        key "chassis-mode";
        leaf chassis-mode {
          type string;
        }
        leaf force {
          tailf:cli-hide-in-submode;
          type empty;
        }
        list power-supply {
          tailf:cli-embed-no-on-delete;
          tailf:cli-suppress-mode;
          key "power-supply-id power-supply-type";
          leaf power-supply-id {
            type string;
          }
          leaf power-supply-type {
            type enumeration {
              enum "dc";
            }
          }
        }
      }
      leaf clli-code {
        type string;
      }
      leaf config-backup {
        type string;
      }
      leaf contact {
        type string;
      }
      leaf coordinates {
        type string;
      }
      container dns {
        tailf:cli-add-mode;
        container address-pref {
          choice choice {
            leaf ipv4-only {
              type empty;
            }
            leaf ipv6-first {
              type empty;
            }
          }
        }
      }
      leaf enable-icmp-vse {
        type empty;
      }
      container ethernet {
        tailf:info
          "Configure system-wide Ethernet parameters";
        tailf:cli-add-mode;
        container efm-oam {
          leaf grace-tx-enable {
            type empty;
          }
        }
        leaf new-qinq-untagged-sap {
          tailf:info
            "Configure Q-IN-Q behavior";
          type empty;
        }
      }
      leaf l4-load-balancing {
        type empty;
      }
      leaf lacp-system-priority {
        type string;
      }
      container lldp {
        tailf:cli-add-mode;
        leaf message-fast-tx {
          type string;
        }
        leaf message-fast-tx-init {
          type string;
        }
        leaf reinit-delay {
          type string;
        }
        leaf tx-credit-max {
          type string;
        }
        leaf tx-hold-multiplier {
          type string;
        }
        leaf tx-interval {
          type string;
        }
        leaf notification-interval {
          type string;
        }
        leaf shutdown {
          tailf:cli-boolean-no;
          default "true";
          type boolean;
        }
      }
      leaf location {
        type string;
      }
      container login-control {
        tailf:cli-add-mode;
        leaf exponential-backoff {
          type empty;
        }
        container ftp {
          tailf:cli-add-mode;
          leaf inbound-max-sessions {
            type string;
          }
        }
        leaf idle-timeout {
          type string;
        }
        leaf idle-timeoutdisable {
          type empty;
        }
        leaf login-banner {
          type empty;
        }
        container motd {
          choice choice {
            leaf url {
              type string;
            }
            leaf text {
              type string;
            }
          }
        }
        container pre-login-message {
          presence "present";
          tailf:cli-sequence-commands;
          tailf:cli-compact-syntax;
          tailf:cli-full-no;
          tailf:cli-embed-no-on-delete;
          leaf login-text-string {
            tailf:cli-drop-node-name;
            tailf:cli-delete-container-on-delete;
            type string;
          }
          leaf name {
            tailf:cli-no-name-on-delete;
            type empty;
          }
        }
        container ssh {
          tailf:cli-add-mode;
          leaf disable-graceful-shutdown {
            type empty;
          }
          leaf inbound-max-sessions {
            type string;
          }
          leaf outbound-max-sessions {
            type string;
          }
          leaf ttl-security {
            type string;
          }
        }
        container telnet {
          tailf:cli-add-mode;
          leaf enable-graceful-shutdown {
            type empty;
          }
          leaf inbound-max-sessions {
            type string;
          }
          leaf outbound-max-sessions {
            type string;
          }
          leaf ttl-security {
            type string;
          }
        }
      }
      container lsr-load-balancing {
        choice choice {
          leaf lbl-only {
            type empty;
          }
          leaf lbl-ip {
            type empty;
          }
          leaf ip-only {
            type empty;
          }
        }
      }
      leaf mc-enh-load-balancing {
        type empty;
      }
      leaf mixed-mode {
        type empty;
      }
      leaf name {
        type string;
      }
      container netconf {
        tailf:cli-add-mode;
        leaf shutdown {
          tailf:cli-boolean-no;
          default "true";
          type boolean;
        }
      }
      container persistence {
        tailf:cli-add-mode;
        container ancp {
          leaf description {
            tailf:cli-embed-no-on-delete;
            tailf:cli-no-value-on-delete;
            type string;
          }
          leaf location {
            type string;
          }
        }
        container application-assurance {
          tailf:cli-add-mode;
          leaf description {
            tailf:cli-embed-no-on-delete;
            tailf:cli-no-value-on-delete;
            type string;
          }
          leaf location {
            type string;
          }
        }
        container dhcp-server {
          tailf:cli-add-mode;
          leaf description {
            tailf:cli-embed-no-on-delete;
            tailf:cli-no-value-on-delete;
            type string;
          }
          leaf location {
            type string;
          }
        }
        container nat-port-forwarding {
          tailf:cli-add-mode;
          leaf description {
            tailf:cli-embed-no-on-delete;
            tailf:cli-no-value-on-delete;
            type string;
          }
          leaf location {
            type string;
          }
        }
        container subscriber-mgmt {
          tailf:cli-add-mode;
          leaf description {
            tailf:cli-embed-no-on-delete;
            tailf:cli-no-value-on-delete;
            type string;
          }
          leaf location {
            type string;
          }
        }
      }
      container snmp {
        tailf:cli-add-mode;
        tailf:cli-embed-no-on-delete;
        leaf engineID {
          type string;
        }
        leaf general-port {
          type uint16;
        }
        leaf packet-size {
          type uint16;
        }
        leaf shutdown {
          tailf:cli-boolean-no;
          default "true";
          type boolean;
        }
      }
      container rollback {
        tailf:info
          "Configure general rollback parameters";
        tailf:cli-add-mode;
        leaf local-max-checkpoints {
          tailf:info
            "Configures the maximum rollback files on compact flash";
          tailf:cli-no-value-on-delete;
          type uint8 {
            range "1..50";
          }
        }
        leaf remote-max-checkpoints {
          tailf:info
            "Configures the maximum rollback files saved at a remote location (ftp)";
          tailf:cli-no-value-on-delete;
          type uint8 {
            range "1..200";
          }
        }
        leaf rescue-location {
          tailf:info
            "Configures the location of the rollback rescue file";
          type string;
        }
        leaf rollback-location {
          tailf:info
            "Configures the location and filename of the rollback checkpoint files";
          type string;
        }
      }
      container time {
        tailf:cli-add-mode;
        container ntp {
          tailf:cli-add-mode;
          leaf authentication-check {
            tailf:info
              "Configure the option to skip the rejection of NTP PDUs";
            type empty;
          }
          list authentication-key {
            tailf:info
              "Configure the authentication key and type used to verify NTP PDUs";
            tailf:cli-embed-no-on-delete;
            tailf:cli-suppress-mode;
            tailf:cli-compact-syntax;
            tailf:cli-sequence-commands;
            key "key-id";
            leaf key-id {
              type uint8 {
                range "1..255";
              }
            }
            leaf key {
              tailf:cli-no-name-on-delete;
              tailf:cli-no-value-on-delete;
              type string {
                length "1..32";
              }
            }
            leaf hash {
              tailf:cli-drop-node-name;
              tailf:cli-no-value-on-delete;
              type enumeration {
                enum "hash";
                enum "hash2";
              }
            }
            leaf type {
              tailf:cli-no-name-on-delete;
              tailf:cli-no-value-on-delete;
              type enumeration {
                enum "des";
                enum "message-digest";
              }
            }
          }
          list server {
            tailf:info
              "Configure NTP to use the specified address as an NTP server";
            tailf:cli-embed-no-on-delete;
            tailf:cli-suppress-mode;
            key "address";
            leaf address {
              type union {
                type inet:ipv4-address;
                type inet:ipv6-address;
              }
            }
            leaf key-id {
              tailf:cli-no-name-on-delete;
              tailf:cli-no-value-on-delete;
              type uint8;
            }
            leaf version {
              tailf:cli-no-name-on-delete;
              tailf:cli-no-value-on-delete;
              type uint8 {
                range "1..4";
              }
            }
            leaf prefer {
              tailf:cli-no-name-on-delete;
              type empty;
            }
          }
          leaf shutdown {
            tailf:cli-boolean-no;
            default "true";
            type boolean;
          }
        }
        container sntp {
          tailf:cli-add-mode;
          leaf broadcast-client {
            type empty;
          }
          container server-address {
            tailf:cli-compact-syntax;
            tailf:cli-sequence-commands;
            leaf ip {
              tailf:cli-drop-node-name;
              type inet:ipv4-address;
            }
            leaf version {
              tailf:cli-drop-node-name;
              tailf:cli-optional-in-sequence;
              type uint8 {
                range "1..3";
              }
            }
            leaf mode {
              tailf:cli-drop-node-name;
              type enumeration {
                enum "normal";
                enum "preferred";
              }
            }
            leaf interval {
              type uint32;
            }
          }
          leaf shutdown {
            tailf:cli-boolean-no;
            default "true";
            type boolean;
          }
        }
        container zone {
          tailf:cli-compact-syntax;
          tailf:cli-sequence-commands;
          leaf name {
            tailf:cli-drop-node-name;
            type string;
          }
          leaf time {
            tailf:cli-drop-node-name;
            type string;
          }
        }
        container dst-zone {
          tailf:cli-add-mode;
          leaf name {
            tailf:cli-drop-node-name;
            tailf:cli-hide-in-submode;
            type string;
          }
          container start {
            tailf:cli-sequence-commands;
            tailf:cli-compact-syntax;
            tailf:cli-no-name-on-delete;
            uses time-stamp;
          }
          container end {
            tailf:cli-sequence-commands;
            tailf:cli-compact-syntax;
            tailf:cli-no-name-on-delete;
            uses time-stamp;
          }
        }
      }
      container thresholds {
        tailf:cli-add-mode;
        container rmon {
          tailf:cli-add-mode;
          leaf alarm {
            type empty;
          }
          leaf event {
            type empty;
          }
        }
      }
      list power-supply {
        tailf:cli-embed-no-on-delete;
        tailf:cli-suppress-mode;
        key "power-supply-id";
        leaf power-supply-id {
          type string;
        }
      }
      container security {
        tailf:info
          "Configure system security related parameters";
        tailf:cli-add-mode;
        container hash-control {
          tailf:info
            "Configure system security hash-control";
          leaf read-version {
            type enumeration {
              enum "1";
              enum "2";
              enum "all";
            }
          }
          leaf write-version {
            type enumeration {
              enum "1";
              enum "2";
            }
          }
        }
        list profile {
          tailf:info
            "Create/delete user profiles";
          tailf:cli-embed-no-on-delete;
          key "name";
          leaf name {
            type string;
          }
          leaf default-action {
            tailf:info
              "Default action for the profile";
            tailf:cli-no-value-on-delete;
            type enumeration {
              enum "deny-all";
              enum "permit-all";
              enum "none";
            }
          }
          list entry {
            tailf:info
              "Match criteria entry for the profile";
            key "entry-id";
            leaf entry-id {
              type uint16 {
                range "1..9999";
              }
            }
            leaf action {
              tailf:info
                "Action to take when a user command matches this entry";
              type enumeration {
                enum "permit";
                enum "deny";
              }
            }
            leaf description {
              tailf:info
                "Description for this entry";
              type string {
                length "1..80";
              }
            }
            leaf match {
              tailf:info
                "Description for this entry";
              type string {
                length "1..256";
              }
            }
          }
        }
        container password {
          tailf:info
            "Configure password related parameters";
          tailf:cli-add-mode;
          leaf health-check {
            tailf:info
              "Enable/disable dynamic monitoring of radius and tacplus";
            tailf:cli-no-value-on-delete;
            type uint16 {
              range "6..1500";
            }
          }
          leaf-list authentication-order {
            tailf:info
              "Sequence in which user password is authenticated";
            tailf:cli-flat-list-syntax;
            type enumeration {
              enum "local";
              enum "radius";
              enum "tacplus";
            }
          }
          container attempts {
            tailf:info
              "Max number of unsuccessful login attempts allowed in a specified time frame";
            tailf:cli-compact-syntax;
            tailf:cli-sequence-commands {
              tailf:cli-reset-all-siblings;
            }
            leaf count {
              tailf:cli-drop-node-name;
              tailf:cli-no-value-on-delete;
              type uint8;
            }
            leaf time {
              tailf:cli-break-sequence-commands;
              tailf:cli-no-value-on-delete;
              tailf:cli-no-name-on-delete;
              type uint8;
            }
            leaf lockout {
              tailf:cli-no-value-on-delete;
              tailf:cli-no-name-on-delete;
              type uint8;
            }
          }
        }
        container radius {
          tailf:info
            "Configure RADIUS authentication parameters";
          tailf:cli-add-mode;
          leaf authorization {
            tailf:info
              "Enable/disable RADIUS command accounting";
            type empty;
          }
          leaf accounting {
            tailf:info
              "Enable/disable RADIUS command authorization";
            type empty;
          }
          list server {
            tailf:info
              "Add/remove a RADIUS server";
            tailf:cli-embed-no-on-delete;
            tailf:cli-suppress-mode;
            tailf:cli-compact-syntax;
            key "server-index";
            leaf server-index {
              tailf:cli-drop-node-name;
              tailf:cli-no-value-on-delete;
              type uint32;
            }
            leaf address {
              tailf:cli-no-value-on-delete;
              mandatory true;
              type inet:ipv4-address;
            }
            leaf secret {
              tailf:cli-no-value-on-delete;
              mandatory true;
              type string;
            }
            leaf type {
              tailf:cli-drop-node-name;
              tailf:cli-no-value-on-delete;
              mandatory true;
              type enumeration {
                enum "hash";
                enum "hash2";
              }
            }
          }
        }
        container tacplus {
          tailf:info
            "Configure TACACS+ authentication parameters for the system";
          tailf:cli-embed-no-on-delete;
          tailf:cli-add-mode;
          container accounting {
            tailf:info
              "Enable/disable TACACS+ command accounting";
            tailf:cli-embed-no-on-delete;
            leaf record-type {
              tailf:cli-no-name-on-delete;
              tailf:cli-no-value-on-delete;
              type enumeration {
                enum "start-stop";
                enum "stop-only";
              }
            }
          }
          container authorization {
            tailf:info
              "Enable/disable TACACS+ command authorization";
            tailf:cli-embed-no-on-delete;
            presence "true";
            leaf use-prix-lvl {
              tailf:cli-no-name-on-delete;
              type empty;
            }
          }
          leaf interactive-authentication {
            tailf:info
              "Enable/disable TACACS+ interactive authentication";
            type empty;
          }
          container priv-lvl-map {
            tailf:info
              "Configure privilege level mapping";
            tailf:cli-embed-no-on-delete;
            tailf:cli-add-mode;
            list priv-lvl {
              tailf:info
                "Configure a user profile for this privilege level";
              tailf:cli-suppress-mode;
              key "lvl";
              leaf lvl {
                type uint8 {
                  range "0..15";
                }
              }
              leaf user-profile {
                tailf:cli-drop-node-name;
                tailf:cli-no-value-on-delete;
                type union {
                  type enumeration {
                    enum "default";
                  }
                  type string;
                }
              }
            }
          }
          list server {
            tailf:info
              "Add/remove a TACACS+ server";
            tailf:cli-suppress-mode;
            tailf:cli-compact-syntax;
            key "server-index";
            leaf server-index {
              type uint8 {
                range "1..5";
              }
            }
            leaf address {
              tailf:cli-no-value-on-delete;
              tailf:cli-no-name-on-delete;
              type union {
                type inet:ipv4-address;
                type inet:ipv6-address;
              }
            }
            leaf secret {
              tailf:cli-no-value-on-delete;
              tailf:cli-no-name-on-delete;
              type string {
                length "1..255";
              }
            }
            leaf hash {
              tailf:cli-drop-node-name;
              tailf:cli-no-value-on-delete;
              default "hash2";
              type enumeration {
                enum "hash";
                enum "hash2";
              }
            }
            leaf port {
              tailf:cli-no-value-on-delete;
              tailf:cli-no-name-on-delete;
              type uint16;
            }
          }
          leaf timeout {
            tailf:info
              "Timeout for a response from the TACACS+ server";
            tailf:cli-no-value-on-delete;
            type uint32;
          }
          leaf use-default-template {
            tailf:info
              "Enable/disable TACACS+ default template";
            type empty;
          }
          leaf shutdown {
            tailf:info
              "Enable/disable TACACS+ protocol operation";
            tailf:cli-boolean-no;
            default "true";
            type boolean;
          }
        }
        leaf telnet-server {
          tailf:info
            "Start/Stop telnet server";
          type empty;
        }
        leaf telnet6-server {
          tailf:info
            "Start/Stop telnet IPv6 server";
          type empty;
        }
        leaf ftp-server {
          tailf:info
            "Start/Stop FTP server";
          type empty;
        }
        leaf per-peer-queuing {
          tailf:info
            "Enable/disable CPM hardware queuing per peer";
          type empty;
        }
        container snmp {
          tailf:info
            "Configure SNMP security parameters";
          tailf:cli-add-mode;
          container access {
            tailf:info
              "Configure access groups for SNMP security";
            tailf:cli-embed-no-on-delete;
            list group {
              tailf:info
                "Group name";
              tailf:cli-suppress-mode;
              tailf:cli-compact-syntax;
              tailf:cli-sequence-commands;
              key "name";
              leaf name {
                type string;
              }
              leaf security-model {
                type enumeration {
                  enum "usm";
                  enum "snmpv1";
                  enum "snmpv2c";
                  enum "snmpv2ac";
                }
              }
              leaf security-level {
                type enumeration {
                  enum "auth-no-privacy";
                }
              }
              leaf read {
                type string;
              }
              leaf notify {
                type string;
              }
            }
          }
          list community {
            tailf:info
              "Create/delete SNMP community strings";
            tailf:cli-suppress-mode;
            tailf:cli-compact-syntax;
            tailf:cli-sequence-commands;
            tailf:cli-embed-no-on-delete;
            key "name";
            leaf name {
              type string;
            }
            leaf type {
              tailf:cli-drop-node-name;
              tailf:cli-no-value-on-delete;
              tailf:cli-optional-in-sequence;
              default "hash2";
              type enumeration {
                enum "hash";
                enum "hash2";
              }
            }
            leaf access-parameters {
              tailf:cli-drop-node-name;
              tailf:cli-no-value-on-delete;
              type enumeration {
                enum "r";
                enum "rw";
                enum "rwa";
                enum "mgmt";
                enum "vpls-mgmt";
              }
            }
            leaf version {
              tailf:cli-no-name-on-delete;
              tailf:cli-no-value-on-delete;
              tailf:cli-optional-in-sequence;
              type enumeration {
                enum "v2c";
                enum "v1";
                enum "both";
              }
            }
            leaf src-access-list {
              tailf:cli-no-name-on-delete;
              tailf:cli-no-value-on-delete;
              tailf:cli-optional-in-sequence;
              type string;
            }
          }
        }
        container source-address {
          tailf:info
            "Configure source address for various applications";
          tailf:cli-add-mode;
          list application {
            tailf:info
              "Configure application to use source address";
            tailf:cli-embed-no-on-delete;
            tailf:cli-suppress-mode;
            key "name";
            leaf name {
              type string;
            }
            leaf address {
              tailf:cli-drop-node-name;
              tailf:cli-no-value-on-delete;
              type union {
                type string;
                type inet:ipv4-address;
              }
            }
          }
        }
        container ssh {
          tailf:info
            "Configure SSH parameters";
          tailf:cli-add-mode;
          leaf preserve-key {
            tailf:info
              "enable/disable persistence of host-key";
            type empty;
          }
          leaf server-shutdown {
            tailf:info
              "start/stop SSH server";
            type empty;
          }
          leaf version {
            tailf:info
              "Configure the SSH version";
            tailf:cli-no-value-on-delete;
            type enumeration {
              enum "1";
              enum "2";
              enum "1-2";
            }
          }
        }
        list user {
          tailf:info
            " Configure a local user";
          tailf:cli-embed-no-on-delete;
          key "user-id";
          leaf user-id {
            type string;
          }
          leaf-list access {
            tailf:info
              "Grant/deny a user access permissions for ftp snmp netconf or console";
            tailf:cli-flat-list-syntax;
            type enumeration {
              enum "console";
              enum "snmp";
              enum "ftp";
              enum "li";
              enum "netconf";
            }
          }
          container console {
            tailf:info
              "Configure user profile membership for the console";
            tailf:cli-add-mode;
            leaf cannot-change-password {
              tailf:info
                "Allow/disallow password changing privileges";
              type empty;
            }
            leaf login-exec {
              tailf:info
                "File to be executed when a user successfully logs in";
              tailf:cli-no-value-on-delete;
              type string;
            }
            list member {
              tailf:info
                " Allow user to access a profile";
              tailf:cli-suppress-mode;
              key "name";
              leaf name {
                type string;
              }
            }
            leaf new-password-at-login {
              tailf:info
                "Enable/disable prompting a user to change password at login";
              type empty;
            }
          }
          leaf home-directory {
            tailf:info
              "Home directory for the user";
            tailf:cli-no-value-on-delete;
            type string;
          }
          container password {
            tailf:info
              "Password for the user";
            tailf:cli-compact-syntax;
            tailf:cli-sequence-commands;
            tailf:cli-embed-no-on-delete;
            leaf id {
              tailf:cli-drop-node-name;
              tailf:cli-no-value-on-delete;
              type string;
            }
            leaf method {
              tailf:cli-drop-node-name;
              tailf:cli-no-value-on-delete;
              type enumeration {
                enum "hash2";
              }
            }
          }
          leaf restricted-to-home {
            tailf:info
              "Restrict user to home directory";
            type empty;
          }
          container snmp {
            tailf:info
              "Configure SNMP group membership for the user";
            tailf:cli-add-mode;
            container authentication {
              tailf:info
                "Authentication in the SNMP model";
              tailf:cli-compact-syntax;
              tailf:cli-sequence-commands;
              tailf:cli-embed-no-on-delete;
              leaf hash {
                tailf:cli-no-value-on-delete;
                tailf:cli-no-name-on-delete;
                type enumeration {
                  enum "md5";
                  enum "sha";
                }
              }
              leaf key-1 {
                tailf:cli-drop-node-name;
                tailf:cli-no-value-on-delete;
                type string;
              }
              leaf privacy {
                tailf:cli-no-value-on-delete;
                tailf:cli-no-name-on-delete;
                type enumeration {
                  enum "none";
                  enum "des-key";
                  enum "aes-128-cfb-key";
                }
              }
              leaf key-2 {
                tailf:cli-drop-node-name;
                tailf:cli-no-value-on-delete;
                type string;
              }
              leaf hashval {
                tailf:cli-drop-node-name;
                tailf:cli-no-value-on-delete;
                type string;
              }
            }
            leaf group {
              tailf:info
                "Associate the user with a group name";
              tailf:cli-no-value-on-delete;
              type string;
            }
          }
        }
        container cpu-protection {
          tailf:info
            "Configure CPU protection";
          tailf:cli-add-mode;
          leaf link-specific-rate {
            tailf:info
              "Configure a link-specific rate for CPU protection";
            tailf:cli-no-value-on-delete;
            type uint32;
          }
          list policy {
            tailf:info
              "Configure a CPU protection policy";
            tailf:cli-embed-no-on-delete;
            key "policy-id";
            leaf policy-id {
              type uint16;
            }
            leaf overall-rate {
              tailf:info
                "Configure an overall packet arrival rate limit";
              type union {
                type enumeration {
                  enum "max";
                }
                type uint32 {
                  range "1..100000000";
                }
              }
            }
          }
          leaf protocol-protection {
            tailf:info
              "Enable/Disable DOS protection of network control protocols";
            type empty;
          }
          leaf port-overall-rate {
            tailf:info
              "Configure a per-port overall rate limit for CPU protect";
            type union {
              type enumeration {
                enum "max";
              }
              type uint32 {
                range "1..100000000";
              }
            }
          }
        }
        container cpm-filter {
          tailf:info
            "Configure a CPM filter";
          tailf:cli-add-mode;
          leaf default-action {
            tailf:info
              "Configure the default filter action";
            type enumeration {
              enum "accept";
              enum "drop";
            }
          }
          container ip-filter {
            tailf:info
              "Configure a CPM IP-filter";
            tailf:cli-add-mode;
            list entry {
              tailf:info
                "Configure ip-filter entry";
              tailf:cli-embed-no-on-delete;
              key "entry-id";
              leaf entry-id {
                type uint16;
              }
              container action {
                tailf:info
                  "Configure action for the filter entry";
                tailf:cli-compact-syntax;
                tailf:cli-embed-no-on-delete;
                choice action-choice {
                  leaf drop {
                    tailf:cli-no-name-on-delete;
                    type empty;
                  }
                  leaf accept {
                    tailf:cli-no-name-on-delete;
                    type empty;
                  }
                  leaf queue {
                    tailf:cli-no-name-on-delete;
                    tailf:cli-no-value-on-delete;
                    type uint16 {
                      range "33..2000";
                    }
                  }
                }
              }
              leaf description {
                tailf:info
                  "Description for this filter entry";
                tailf:cli-no-value-on-delete;
                type string {
                  length "1..80";
                }
              }
              leaf log {
                tailf:info
                  "Configure log for the filter entry";
                tailf:cli-no-value-on-delete;
                type uint16;
              }
              container match {
                tailf:info
                  "Configure match criteria for this ip filter entry";
                tailf:cli-add-mode;
                tailf:cli-embed-no-on-delete;
                leaf protocol {
                  tailf:cli-hide-in-submode;
                  tailf:cli-no-name-on-delete;
                  tailf:cli-no-value-on-delete;
                  type protocol;
                }
                leaf dscp {
                  tailf:info
                    "Configure DSCP match condition";
                  tailf:cli-no-value-on-delete;
                  type dscp-type;
                }
                container dst-ip {
                  tailf:info
                    "Configure dest. ip match condition";
                  tailf:cli-embed-no-on-delete;
                  tailf:cli-compact-syntax;
                  tailf:cli-sequence-commands;
                  uses filter-match-ip-grouping;
                }
                container dst-port {
                  tailf:info
                    "Configure dest. port match condition";
                  tailf:cli-embed-no-on-delete;
                  tailf:cli-compact-syntax;
                  tailf:cli-sequence-commands;
                  uses cpm-filter-match-port-grouping;
                }
                leaf fragment {
                  tailf:info
                    "Configure fragmentation match condition";
                  tailf:cli-no-value-on-delete;
                  type boolean;
                }
                leaf icmp-code {
                  tailf:info
                    "Configure ICMP code match condition";
                  tailf:cli-no-value-on-delete;
                  type uint32;
                }
                leaf icmp-type {
                  tailf:info
                    "Configure ICMP type match condition";
                  tailf:cli-no-value-on-delete;
                  type icmp-type;
                }
                container ip-option {
                  tailf:info
                    "Configure ip-option match condition";
                  tailf:cli-embed-no-on-delete;
                  tailf:cli-compact-syntax;
                  leaf value {
                    tailf:cli-drop-node-name;
                    tailf:cli-no-value-on-delete;
                    type uint8;
                  }
                  leaf mask {
                    tailf:cli-drop-node-name;
                    tailf:cli-no-value-on-delete;
                    type uint8;
                  }
                }
                leaf multiple-option {
                  tailf:info
                    "Configure multiple-option match condition";
                  tailf:cli-no-value-on-delete;
                  type boolean;
                }
                leaf option-present {
                  tailf:info
                    "Configure option-present match condition";
                  tailf:cli-no-value-on-delete;
                  type boolean;
                }
                container port {
                  tailf:info
                    "Configure port match condition";
                  tailf:cli-embed-no-on-delete;
                  tailf:cli-compact-syntax;
                  tailf:cli-sequence-commands;
                  uses cpm-filter-match-port-grouping;
                }
                leaf router {
                  tailf:info
                    "Match a router|service-id";
                  tailf:cli-no-value-on-delete;
                  type union {
                    type string {
                      length "1..32";
                    }
                    type uint32 {
                      range "1..2147483647";
                    }
                  }
                }
                container src-ip {
                  tailf:info
                    "Configure source ip match condition";
                  tailf:cli-embed-no-on-delete;
                  tailf:cli-compact-syntax;
                  tailf:cli-sequence-commands;
                  uses filter-match-ip-grouping;
                }
                container src-port {
                  tailf:info
                    "Configure source port match condition";
                  tailf:cli-embed-no-on-delete;
                  tailf:cli-compact-syntax;
                  tailf:cli-sequence-commands;
                  uses cpm-filter-match-port-grouping;
                }
                leaf tcp-ack {
                  tailf:info
                    "Configure TCP ACK match condition";
                  tailf:cli-no-value-on-delete;
                  type boolean;
                }
                leaf tcp-syn {
                  tailf:info
                    " Configure TCP SYN match condition";
                  tailf:cli-no-value-on-delete;
                  type boolean;
                }
              }
            }
            leaf shutdown {
              tailf:info
                "Set the admin state of the IP filter";
              tailf:cli-boolean-no;
              default "true";
              type boolean;
            }
          }
          container ipv6-filter {
            tailf:info
              "Configure a CPM IPv6-filter";
            tailf:cli-add-mode;
            list entry {
              tailf:info
                "Configure IPv6-filter entry";
              tailf:cli-embed-no-on-delete;
              key "entry-id";
              leaf entry-id {
                type uint16;
              }
              container action {
                tailf:info
                  "Configure action for the IPv6-filter entry";
                tailf:cli-compact-syntax;
                tailf:cli-embed-no-on-delete;
                choice action-choice {
                  leaf drop {
                    tailf:cli-no-name-on-delete;
                    type empty;
                  }
                  leaf accept {
                    tailf:cli-no-name-on-delete;
                    type empty;
                  }
                  leaf queue {
                    tailf:cli-no-name-on-delete;
                    tailf:cli-no-value-on-delete;
                    type uint16 {
                      range "33..2000";
                    }
                  }
                }
              }
              leaf description {
                tailf:info
                  "Description for this filter entry";
                tailf:cli-no-value-on-delete;
                type string {
                  length "1..80";
                }
              }
              leaf log {
                tailf:info
                  "Configure log for the IPv6-filter entry";
                tailf:cli-no-value-on-delete;
                type uint16;
              }
              container match {
                tailf:info
                  "Configure match criteria for this IPv6 filter entry";
                tailf:cli-add-mode;
                tailf:cli-embed-no-on-delete;
                leaf next-header {
                  tailf:cli-hide-in-submode;
                  tailf:cli-no-name-on-delete;
                  tailf:cli-no-value-on-delete;
                  type protocol;
                }
                leaf dscp {
                  tailf:info
                    "Configure DSCP match condition";
                  tailf:cli-no-value-on-delete;
                  type dscp-type;
                }
                leaf dst-ip {
                  tailf:info
                    "Configure dest. IPv6 addr  match condition";
                  tailf:cli-no-value-on-delete;
                  type union {
                    type tailf:ipv6-address-and-prefix-length;
                    type string;
                  }
                }
                container dst-port {
                  tailf:info
                    "Configure dest. port match condition";
                  tailf:cli-embed-no-on-delete;
                  tailf:cli-compact-syntax;
                  tailf:cli-sequence-commands;
                  uses cpm-filter-match-port-grouping;
                }
                leaf flow-label {
                  tailf:info
                    "Configure flow label match condition";
                  tailf:cli-no-value-on-delete;
                  type uint32 {
                    range "0..1048575";
                  }
                }
                leaf hop-by-hop-opt {
                  tailf:info
                    "Configure hop by hop match condition";
                  tailf:cli-no-value-on-delete;
                  type boolean;
                }
                leaf icmp-code {
                  tailf:info
                    "Configure ICMP code match condition";
                  tailf:cli-no-value-on-delete;
                  type uint32;
                }
                leaf icmp-type {
                  tailf:info
                    "Configure ICMP type match condition";
                  tailf:cli-no-value-on-delete;
                  type icmpv6-type;
                }
                container port {
                  tailf:info
                    "Configure port match condition";
                  tailf:cli-embed-no-on-delete;
                  tailf:cli-compact-syntax;
                  tailf:cli-sequence-commands;
                  uses cpm-filter-match-port-grouping;
                }
                leaf router {
                  tailf:info
                    "Match a router|service-id";
                  tailf:cli-no-value-on-delete;
                  type union {
                    type string {
                      length "1..32";
                    }
                    type uint32 {
                      range "1..2147483647";
                    }
                  }
                }
                container src-ip {
                  tailf:info
                    "Configure source IPv6 address match condition";
                  tailf:cli-embed-no-on-delete;
                  tailf:cli-compact-syntax;
                  tailf:cli-sequence-commands;
                  uses filter-match-ipv6-grouping;
                }
                container src-port {
                  tailf:info
                    "Configure source port match condition";
                  tailf:cli-embed-no-on-delete;
                  tailf:cli-compact-syntax;
                  tailf:cli-sequence-commands;
                  uses cpm-filter-match-port-grouping;
                }
                leaf tcp-ack {
                  tailf:info
                    "Configure TCP ACK match condition";
                  tailf:cli-no-value-on-delete;
                  type boolean;
                }
                leaf tcp-syn {
                  tailf:info
                    "Configure TCP SYN match condition";
                  tailf:cli-no-value-on-delete;
                  type boolean;
                }
              }
            }
            leaf shutdown {
              tailf:info
                "Set the admin state of the IPv6 filter";
              tailf:cli-boolean-no;
              default "false";
              type boolean;
            }
          }
        }
        container cpm-queue {
          tailf:info
            "Configure a CPM queue";
          tailf:cli-add-mode;
          list queue {
            tailf:info
              "Configure a Queue";
            tailf:cli-embed-no-on-delete;
            key "queue-id";
            leaf queue-id {
              type uint32;
            }
            container rate {
              tailf:info
                "Configure Rate";
              tailf:cli-compact-syntax;
              tailf:cli-sequence-commands;
              tailf:cli-embed-no-on-delete;
              leaf value {
                tailf:cli-drop-node-name;
                tailf:cli-no-value-on-delete;
                type union {
                  type enumeration {
                    enum "max";
                  }
                  type uint32 {
                    range "1..100000000";
                  }
                }
              }
              leaf cir {
                tailf:cli-no-value-on-delete;
                tailf:cli-no-name-on-delete;
                type union {
                  type enumeration {
                    enum "max";
                  }
                  type uint32 {
                    range "0..100000000";
                  }
                }
              }
            }
          }
        }
        container management-access-filter {
          tailf:info
            "Configure management access filters";
          tailf:cli-add-mode;
          container ip-filter {
            tailf:info
              "Configure a management access IP-filter";
            tailf:cli-add-mode;
            leaf default-action {
              tailf:info
                "Default-action for the management-access-filter";
              tailf:cli-embed-no-on-delete;
              type filter-action;
            }
            list entry {
              tailf:info
                "Match criteria entry for the management-access-filter";
              tailf:cli-embed-no-on-delete;
              key "entry-name";
              leaf entry-name {
                type string;
              }
              leaf action {
                tailf:info
                  "Action to take when a packet matches this entry";
                tailf:cli-no-value-on-delete;
                type filter-action;
              }
              leaf description {
                tailf:info
                  "Description for this entry";
                tailf:cli-no-value-on-delete;
                type string;
              }
              leaf src-ip {
                tailf:info
                  "Source IP address of packets to match";
                tailf:cli-no-value-on-delete;
                type union {
                  type tailf:ipv4-address-and-prefix-length;
                  type string;
                }
              }
              leaf dst-port {
                tailf:info
                  "TCP/UDP port number or port range to match";
                tailf:cli-no-value-on-delete;
                type uint16;
              }
              leaf src-port {
                tailf:info
                  "Source physical interface to match";
                tailf:cli-no-value-on-delete;
                type string;
              }
              leaf router {
                tailf:info
                  "Configure router";
                tailf:cli-no-value-on-delete;
                type leafref {
                  path "/ncs:devices/ncs:device/ncs:config/alu:router/router-name" {
                    tailf:xpath-root 3;
                  }
                }
              }
            }
            leaf shutdown {
              tailf:info
                "Start/shutdown the management-access-filter";
              tailf:cli-boolean-no;
              default "true";
              type boolean;
            }
          }
          container ipv6-filter {
            tailf:info
              "Configure a management access IPv6-filter";
            tailf:cli-add-mode;
            leaf default-action {
              tailf:info
                "Default-action for the management-access-filter";
              tailf:cli-embed-no-on-delete;
              tailf:cli-no-value-on-delete;
              type filter-action;
            }
            list entry {
              tailf:info
                "Match criteria entry for the management-access-filter";
              tailf:cli-embed-no-on-delete;
              key "entry-name";
              leaf entry-name {
                type string;
              }
              leaf action {
                tailf:info
                  " Action to take when a packet matches this entry";
                tailf:cli-no-value-on-delete;
                type filter-action;
              }
              leaf description {
                tailf:info
                  "Description for this entry";
                tailf:cli-no-value-on-delete;
                type string;
              }
              leaf src-ip {
                tailf:info
                  "Source IP address of packets to match";
                tailf:cli-no-value-on-delete;
                type union {
                  type tailf:ipv6-address-and-prefix-length;
                  type string;
                }
              }
              leaf dst-port {
                tailf:info
                  "TCP/UDP port number or port range to match";
                tailf:cli-no-value-on-delete;
                type uint16;
              }
              leaf src-port {
                tailf:info
                  "Source physical interface to match";
                tailf:cli-no-value-on-delete;
                type string;
              }
            }
            leaf shutdown {
              tailf:info
                "Start/shutdown the management-access-filter";
              tailf:cli-boolean-no;
              default "true";
              type boolean;
            }
          }
        }
        leaf vprn-network-exceptions {
          tailf:info
            "Configure rate for MPLS Exception messages";
          type empty;
        }
      }
      container sync-if-timing {
        tailf:info
          "Configure synchronous interface timing";
        tailf:cli-add-mode;
        container begin {
          tailf:info
            "Switch to edit mode for sync interface timing";
          tailf:cli-add-mode;
          tailf:cli-explicit-exit;
          tailf:cli-exit-command "commit";
          leaf description {
            type string;
          }
        }
      }
    }
    container redundancy {
      tailf:ncs-device-type "cli-ned";
      tailf:display-when "not(../../ncs:module) or ../../ncs:module[ncs:name='tailf-ned-alu-sr']";
      tailf:info
        "Configure redundancy";
      tailf:cli-add-mode;
      container multi-chassis {
        tailf:info
          "Configure multi-chassis parameters";
        tailf:cli-add-mode;
        list peer {
          tailf:info
            "Configure a multi-chassis redundancy peer";
          tailf:cli-embed-no-on-delete;
          key "address";
          leaf address {
            type inet:ipv4-address;
          }
          container mc-lag {
            tailf:info
              "Configure a Multi-Chassis LAG";
            tailf:cli-embed-no-on-delete;
            tailf:cli-add-mode;
            leaf shutdown {
              tailf:info
                "Administratively enable/disable the MC-LAG";
              tailf:cli-boolean-no;
              default "true";
              type boolean;
            }
          }
          leaf shutdown {
            tailf:info
              "Administratively enable/disable the multi-chassis peer";
            tailf:cli-boolean-no;
            default "true";
            type boolean;
          }
        }
      }
      leaf synchronize {
        tailf:info
          "Configure redundancy synchronization parameters";
        tailf:cli-no-value-on-delete;
        type enumeration {
          enum "boot-env";
          enum "config";
        }
      }
    }
    container filter {
      tailf:ncs-device-type "cli-ned";
      tailf:display-when "not(../../ncs:module) or ../../ncs:module[ncs:name='tailf-ned-alu-sr']";
      tailf:info
        "Configuration of filters";
      tailf:cli-add-mode;
      list ip-filter {
        tailf:info
          "Configure an IP-filter";
        tailf:cli-embed-no-on-delete;
        key "ip-filter-name";
        leaf ip-filter-name {
          type string;
        }
        list embed-filter {
          tailf:info
            "Configure embedded filter";
          tailf:cli-embed-no-on-delete;
          tailf:cli-compact-syntax;
          tailf:cli-suppress-mode;
          tailf:cli-sequence-commands;
          key "embed-filter-name";
          leaf embed-filter-name {
            tailf:non-strict-leafref {
              path "/ncs:devices/ncs:device/ncs:config/alu:filter/ip-filter/ip-filter-name" {
                tailf:xpath-root 3;
              }
            }
            type string;
          }
          leaf offset {
            tailf:cli-no-value-on-delete;
            tailf:cli-no-name-on-delete;
            type uint32;
          }
          leaf status {
            tailf:cli-drop-node-name;
            tailf:cli-no-value-on-delete;
            type enumeration {
              enum "active";
              enum "inactive";
            }
          }
        }
        leaf default-action {
          tailf:info
            "Configure default-action for the filter";
          tailf:cli-no-value-on-delete;
          type enumeration {
            enum "drop";
            enum "forward";
          }
        }
        leaf scope {
          tailf:info
            "Configure scope for this filter";
          tailf:cli-no-value-on-delete;
          type enumeration {
            enum "template";
            enum "exclusive";
            enum "embedded";
          }
        }
        leaf description {
          tailf:info
            "Description for this ip-filter";
          tailf:cli-no-value-on-delete;
          type string;
        }
        list entry {
          tailf:info
            "Configure ip-filter entry";
          tailf:cli-embed-no-on-delete;
          uses ip-filter-entry-grouping;
          key "entry-name";
          ordered-by user;
          container action {
            tailf:info
              "Configure action for the filter entry";
            tailf:cli-compact-syntax;
            tailf:cli-sequence-commands;
            tailf:cli-embed-no-on-delete;
            choice action-choice {
              case aa {
                leaf drop {
                  tailf:cli-no-name-on-delete;
                  type empty;
                }
              }
              case ab {
                leaf nat {
                  tailf:cli-no-name-on-delete;
                  type empty;
                }
              }
              case ac {
                leaf http-redirect {
                  tailf:cli-no-name-on-delete;
                  tailf:cli-no-value-on-delete;
                  type string;
                }
              }
              case ad {
                container forward {
                  tailf:cli-no-name-on-delete;
                  presence "true";
                  container next-hop {
                    tailf:cli-no-name-on-delete;
                    choice next-hop-choice {
                      case na {
                        leaf ip-address {
                          tailf:cli-drop-node-name;
                          tailf:cli-no-value-on-delete;
                          type inet:ipv4-address;
                        }
                      }
                      case nb {
                        leaf indirect {
                          tailf:cli-no-name-on-delete;
                          tailf:cli-no-value-on-delete;
                          type inet:ipv4-address;
                        }
                      }
                      case nc {
                        leaf interface {
                          tailf:cli-no-name-on-delete;
                          tailf:cli-no-value-on-delete;
                          type string;
                        }
                      }
                    }
                  }
                  leaf sap {
                    tailf:cli-no-name-on-delete;
                    tailf:cli-no-value-on-delete;
                    type string;
                  }
                  leaf sdp {
                    tailf:cli-no-name-on-delete;
                    tailf:cli-no-value-on-delete;
                    type string;
                  }
                  leaf redirect-policy {
                    tailf:cli-no-name-on-delete;
                    tailf:cli-no-value-on-delete;
                    type string;
                  }
                }
              }
            }
          }
        }
      }
      list ipv6-filter {
        tailf:info
          "Configure an IPv6-filter";
        tailf:cli-embed-no-on-delete;
        key "ip-filter-name";
        leaf ip-filter-name {
          type string;
        }
        leaf default-action {
          tailf:info
            "Configure default-action for the IPv6-filter";
          tailf:cli-no-value-on-delete;
          type enumeration {
            enum "forward";
            enum "drop";
          }
        }
        list embed-filter {
          tailf:info
            "Configure embed filter for the IPv6-filter";
          tailf:cli-embed-no-on-delete;
          tailf:cli-compact-syntax;
          tailf:cli-suppress-mode;
          tailf:cli-sequence-commands;
          key "embed-filter-name";
          leaf embed-filter-name {
            tailf:non-strict-leafref {
              path "/ncs:devices/ncs:device/ncs:config/alu:filter/ipv6-filter/ip-filter-name" {
                tailf:xpath-root 3;
              }
            }
            type string;
          }
          leaf offset {
            tailf:cli-embed-no-on-delete;
            tailf:cli-no-value-on-delete;
            tailf:cli-no-name-on-delete;
            type uint32;
          }
          leaf status {
            tailf:cli-drop-node-name;
            tailf:cli-embed-no-on-delete;
            tailf:cli-no-value-on-delete;
            type enumeration {
              enum "active";
              enum "inactive";
            }
          }
        }
        leaf scope {
          type enumeration {
            enum "embedded";
            enum "exclusive";
            enum "template";
          }
        }
        leaf description {
          tailf:info
            "Description for the IPv6-filter";
          tailf:cli-no-value-on-delete;
          type string;
        }
        list entry {
          tailf:info
            "Configure an IPv6-filter entry";
          tailf:cli-embed-no-on-delete;
          uses ipv6-filter-entry-grouping;
          key "entry-name";
          leaf action {
            tailf:info
              " Configure action for the IPv6-filter entry";
            type enumeration {
              enum "drop";
              enum "forward";
            }
          }
        }
      }
      list mac-filter {
        tailf:info
          "Configure a mac-filter";
        tailf:cli-recursive-delete;
        tailf:cli-embed-no-on-delete;
        key "mac-filter-name";
        leaf mac-filter-name {
          type string;
        }
        leaf default-action {
          tailf:info
            "Configure default-action for the filter";
          type enumeration {
            enum "drop";
            enum "forward";
          }
        }
        leaf scope {
          tailf:info
            "Configure scope for this filter";
          tailf:cli-no-value-on-delete;
          type enumeration {
            enum "exclusive";
            enum "template";
          }
        }
        leaf description {
          tailf:info
            "Description for this mac-filter";
          tailf:cli-no-value-on-delete;
          type string;
        }
        list entry {
          tailf:info
            "Configure mac-filter entry";
          tailf:cli-recursive-delete;
          tailf:cli-embed-no-on-delete;
          key "entry-name";
          leaf entry-name {
            type string;
          }
          leaf description {
            tailf:info
              "Description for this filter entry";
            tailf:cli-no-value-on-delete;
            type string;
          }
          container match {
            tailf:info
              "Configure match criteria for this mac filter entry";
            tailf:cli-add-mode;
            container dst-mac {
              tailf:info
                "Configure dest. mac match condition";
              tailf:cli-embed-no-on-delete;
              leaf mac {
                tailf:cli-drop-node-name;
                tailf:cli-no-value-on-delete;
                type string;
              }
              leaf mask {
                tailf:cli-drop-node-name;
                tailf:cli-no-value-on-delete;
                type string;
              }
            }
            container src-mac {
              tailf:info
                "Configure source mac match condition";
              tailf:cli-embed-no-on-delete;
              leaf mac {
                tailf:cli-drop-node-name;
                tailf:cli-no-value-on-delete;
                type string;
              }
              leaf mask {
                tailf:cli-drop-node-name;
                tailf:cli-no-value-on-delete;
                type string;
              }
            }
            leaf frame-type {
              tailf:cli-hide-in-submode;
              tailf:cli-no-value-on-delete;
              tailf:cli-no-name-on-delete;
              type enumeration {
                enum "802dot3";
                enum "802dot2-llc";
                enum "802dot2-snap";
                enum "ethernet_II";
              }
            }
            leaf etype {
              tailf:info
                "Configure e-type match condition";
              tailf:cli-no-value-on-delete;
              when '../frame-type' {
                tailf:xpath-root 3;
              }
              type string;
            }
          }
          container action {
            tailf:info
              "Configure action for the filter entry";
            tailf:cli-compact-syntax;
            choice choice {
              case drop {
                leaf drop {
                  type empty;
                }
              }
              case forward {
                leaf forward {
                  type empty;
                }
                leaf sap {
                  type string;
                }
              }
            }
          }
          leaf log {
            tailf:info
              "Configure log for the filter entry";
            tailf:cli-no-value-on-delete;
            type uint32;
          }
        }
      }
      container match-list {
        tailf:info
          "Configure a match-list for use in a filter";
        tailf:cli-add-mode;
        list ip-prefix-list {
          tailf:info
            "Configure an ip prefix list";
          tailf:cli-embed-no-on-delete;
          key "name";
          leaf name {
            type string;
          }
          leaf description {
            tailf:info
              "Description for this prefix list";
            tailf:cli-no-value-on-delete;
            type string;
          }
          list prefix {
            tailf:info
              "Create/delete a prefix entry in the prefix list";
            tailf:cli-embed-no-on-delete;
            tailf:cli-suppress-mode;
            key "pfx";
            leaf pfx {
              type tailf:ipv4-address-and-prefix-length;
            }
          }
        }
        list ipv6-prefix-list {
          tailf:info
            "Configure an ipv6 prefix list";
          tailf:cli-embed-no-on-delete;
          key "name";
          leaf name {
            type string;
          }
          leaf description {
            tailf:info
              "Description for this prefix list";
            tailf:cli-no-value-on-delete;
            type string;
          }
          list prefix {
            tailf:info
              "Create/delete a prefix entry in the prefix list";
            tailf:cli-embed-no-on-delete;
            tailf:cli-suppress-mode;
            key "pfx";
            leaf pfx {
              type tailf:ipv6-address-and-prefix-length;
            }
          }
        }
      }
      list log {
        key "log-id";
        leaf log-id {
          type uint32;
        }
        leaf description {
          type string;
        }
        container destination {
          choice choice {
            leaf memory {
              type uint32;
            }
            leaf syslog {
              type uint32;
            }
          }
        }
      }
    }
    container test-oam {
      tailf:ncs-device-type "cli-ned";
      tailf:display-when "not(../../ncs:module) or ../../ncs:module[ncs:name='tailf-ned-alu-sr']";
      tailf:info
        "Configure Operations, Administration, and Maintenance test parameters";
      tailf:cli-add-mode;
      container twamp {
        tailf:info
          "Configure the Two Way Active Measurement Protocol (TWAMP)";
        tailf:cli-add-mode;
        container server {
          tailf:info
            "Configure the TWAMP server";
          tailf:cli-add-mode;
          tailf:cli-recursive-delete;
          leaf inactivity-timeout {
            tailf:info
              "Configure the inactivity timeout for the TWAMP server";
            tailf:cli-no-value-on-delete;
            type uint16 {
              range "60..3600";
            }
            default "900";
          }
          leaf max-conn-server {
            tailf:info
              "Configure the maximum number of control connections supported by the TWAMP server";
            tailf:cli-no-value-on-delete;
            type uint8 {
              range "0..64";
            }
            default "32";
          }
          leaf max-sess-server {
            tailf:info
              "Configure the maximum number of sessions supported by the TWAMP server";
            tailf:cli-no-value-on-delete;
            type uint8 {
              range "0..64";
            }
            default "32";
          }
          list prefix {
            key "ip-prefix";
            leaf ip-prefix {
              tailf:cli-drop-node-name;
              type tailf:ip-address-and-prefix-length;
            }
            leaf description {
              tailf:info
                "Configure a description for the prefix";
              tailf:cli-no-value-on-delete;
              type string {
                length "1..80";
              }
            }
            leaf max-conn-prefix {
              tailf:info
                "Configure the maximum number of TWAMP control connections supported for the prefix";
              tailf:cli-no-value-on-delete;
              type uint8 {
                range "0..64";
              }
              default "32";
            }
            leaf max-sess-prefix {
              tailf:info
                "Configure the maximum number of TWAMP sessions supported for the prefix";
              tailf:cli-no-value-on-delete;
              type uint8 {
                range "0..64";
              }
              default "32";
            }
          }
          leaf shutdown {
            tailf:cli-boolean-no;
            default "true";
            type boolean;
          }
        }
      }
    }
    container mirror {
      tailf:ncs-device-type "cli-ned";
      tailf:display-when "not(../../ncs:module) or ../../ncs:module[ncs:name='tailf-ned-alu-sr']";
      tailf:info
        "Configure mirror destinations";
      tailf:cli-add-mode;
      list mirror-dest {
        tailf:info
          "Configure a mirror destination";
        tailf:cli-recursive-delete;
        tailf:cli-embed-no-on-delete;
        key "service-id";
        leaf service-id {
          type union {
            type uint32 {
              range "1..2147483690";
            }
            type string {
              length "1..64";
            }
          }
        }
        leaf mirror-type {
          tailf:cli-hide-in-submode;
          type enumeration {
            enum "ether";
            enum "frame-relay";
            enum "ppp";
            enum "ip-only";
            enum "atm-sdu";
            enum "satop-e1";
            enum "satop-t1";
            enum "cesopsn";
            enum "cesopsn-cas";
          }
        }
        leaf type {
          tailf:cli-no-name-on-delete;
          tailf:cli-no-value-on-delete;
          tailf:cli-hide-in-submode;
          type enumeration {
            enum "ether";
            enum "frame-relay";
            enum "ppp";
            enum "ip-only";
            enum "atm-sdu";
            enum "satop-e1";
            enum "satop-t1";
            enum "cesopsn";
            enum "cesopsn-cas";
          }
        }
        leaf description {
          tailf:info
            "Description for this mirror destination";
          tailf:cli-embed-no-on-delete;
          tailf:cli-no-value-on-delete;
          type string;
        }
        leaf enable-port-id {
          tailf:info
            "Include port-id of the system in the packet";
          tailf:cli-embed-no-on-delete;
          type empty;
        }
        container encap {
          tailf:info
            "Encapsulation header";
          tailf:cli-add-mode;
          list layer-3-encap {
            tailf:info
              "Layer-3 header encapsulation";
            tailf:cli-embed-no-on-delete;
            key "encap";
            max-elements 2;
            leaf encap {
              type enumeration {
                enum "ip-udp-shim";
                enum "ip-gre";
              }
            }
          }
        }
        list endpoint {
          tailf:info
            "Configure a service end-point";
          tailf:cli-embed-no-on-delete;
          key "endpoint-name";
          leaf endpoint-name {
            type string {
              length "1..32";
            }
          }
          leaf description {
            tailf:info
              "Description for the service end-point";
            tailf:cli-embed-no-on-delete;
            tailf:cli-no-value-on-delete;
            type string;
          }
          leaf revert-time {
            tailf:info
              "Configure the time to wait before reverting to primary  spoke-sdp";
            tailf:cli-embed-no-on-delete;
            tailf:cli-no-value-on-delete;
            type union {
              type uint16 {
                range "0..600";
              }
              type enumeration {
                enum "infinite";
              }
            }
          }
        }
        leaf fc {
          tailf:info
            "Configure forwarding class for destination traffic";
          tailf:cli-embed-no-on-delete;
          tailf:cli-no-value-on-delete;
          type enumeration {
            enum "be";
            enum "l2";
            enum "af";
            enum "l1";
            enum "h2";
            enum "ef";
            enum "h1";
            enum "nc";
          }
        }
        container isa-aa-group {
          tailf:info
            "Specify ISA Application Assurance Group";
          tailf:cli-embed-no-on-delete;
          leaf aa-group-id {
            tailf:cli-drop-node-name;
            tailf:cli-no-value-on-delete;
            type uint8 {
              range "1..255";
            }
          }
          leaf traffic-direction {
            tailf:cli-drop-node-name;
            tailf:cli-no-value-on-delete;
            type enumeration {
              enum "from-subscriber";
              enum "to-subscriber";
            }
          }
        }
        container remote-source {
          tailf:info
            "Enable/disable remote-source";
          tailf:cli-add-mode;
          leaf far-end {
            tailf:info
              "Configure Mirror far-end";
            tailf:cli-embed-no-on-delete;
            tailf:cli-no-value-on-delete;
            type inet:ipv4-address;
          }
          list spoke-sdp {
            tailf:info
              "Specify SDP <sdp-id>:<vc-id>";
            tailf:cli-embed-no-on-delete;
            tailf:cli-key-format "$(1):$(2)";
            key "sdp-id vc-id";
            leaf sdp-id {
              type uint32;
              tailf:non-strict-leafref {
                path "/ncs:devices/ncs:device/ncs:config/alu:service/sdp/sdp-id" {
                  tailf:xpath-root 3;
                }
              }
            }
            leaf vc-id {
              type uint32;
            }
            leaf endpoint {
              tailf:cli-hide-in-submode;
              tailf:cli-no-name-on-delete;
              tailf:cli-no-value-on-delete;
              type string {
                length "1..32";
              }
            }
            leaf shutdown {
              tailf:cli-boolean-no;
              default "true";
              type boolean;
            }
          }
        }
        list sap {
          tailf:info
            "Specify SAP";
          tailf:cli-embed-no-on-delete;
          key "sap-id";
          leaf sap-id {
            type string;
          }
          container cem {
            tailf:info
              "Configure CEM properties";
            tailf:cli-add-mode;
            container packet {
              tailf:cli-embed-no-on-delete;
              leaf jitter-buffer {
                tailf:cli-no-name-on-delete;
                tailf:cli-no-value-on-delete;
                type uint8 {
                  range "1..250";
                }
              }
              leaf bytes {
                tailf:cli-no-name-on-delete;
                tailf:cli-no-value-on-delete;
                type uint16 {
                  range "16..2048";
                }
              }
            }
            leaf rtp-header {
              tailf:cli-no-name-on-delete;
              type empty;
            }
          }
          container egress {
            tailf:info
              "Configure SAP egress policies";
            tailf:cli-add-mode;
            container ip-mirror {
              tailf:info
                "Configure IP Mirror information";
              tailf:cli-add-mode;
              leaf sa-mac {
                tailf:cli-embed-no-on-delete;
                type ieee-mac;
              }
            }
            leaf qos {
              tailf:cli-embed-no-on-delete;
              type uint16;
              tailf:non-strict-leafref {
                path "/ncs:devices/ncs:device/ncs:config/alu:qos/sap-egress/policy-id" {
                  tailf:xpath-root 3;
                }
              }
            }
          }
        }
        leaf service-name {
          tailf:info
            "Configure a service-name";
          tailf:cli-embed-no-on-delete;
          tailf:cli-no-value-on-delete;
          type string {
            length "1..64";
          }
        }
        leaf shutdown {
          tailf:info
            "Administratively enable/disable the mirror service";
          tailf:cli-boolean-no;
          default "true";
          type boolean;
        }
        leaf slice-size {
          tailf:info
            "Configure slice-size";
          tailf:cli-embed-no-on-delete;
          tailf:cli-no-value-on-delete;
          type uint16 {
            range "128..9216";
          }
        }
        list spoke-sdp {
          tailf:info
            "Specify SDP <sdp-id>:<vc-id>";
          tailf:cli-key-format "$(1):$(2)";
          key "sdp-id vc-id";
          leaf sdp-id {
            type uint32;
            tailf:non-strict-leafref {
              path "/ncs:devices/ncs:device/ncs:config/alu:service/sdp/sdp-id" {
                tailf:xpath-root 3;
              }
            }
          }
          leaf vc-id {
            type uint32;
          }
          leaf endpoint {
            tailf:cli-hide-in-submode;
            tailf:cli-no-name-on-delete;
            tailf:cli-no-value-on-delete;
            type string {
              length "1..32";
            }
          }
          leaf control-word {
            tailf:cli-embed-no-on-delete;
            type empty;
          }
          leaf precedence {
            tailf:cli-embed-no-on-delete;
            tailf:cli-no-value-on-delete;
            type enumeration {
              enum "1";
              enum "2";
              enum "3";
              enum "4";
              enum "primary";
            }
          }
          container egress {
            tailf:info
              "Spoke SDP egress configuration";
            tailf:cli-add-mode;
            container l2tpv3 {
              tailf:cli-no-name-on-delete;
              leaf cookie {
                tailf:cli-no-name-on-delete;
                tailf:cli-no-value-on-delete;
                type string;
              }
            }
            leaf vc-label {
              tailf:cli-embed-no-on-delete;
              tailf:cli-no-value-on-delete;
              type uint32 {
                range "16..1048575";
              }
            }
          }
          container ingress {
            tailf:info
              "Spoke SDP ingress configuration";
            tailf:cli-add-mode;
            leaf vc-label {
              tailf:cli-embed-no-on-delete;
              tailf:cli-no-value-on-delete;
              type uint32 {
                range "2048..18431";
              }
            }
          }
          leaf shutdown {
            tailf:cli-boolean-no;
            default "true";
            type boolean;
          }
        }
      }
    }
    container saa {
      tailf:ncs-device-type "cli-ned";
      tailf:display-when "not(../../ncs:module) or ../../ncs:module[ncs:name='tailf-ned-alu-sr']";
      tailf:info
        "Configure Service Assurance Agent Tests";
      tailf:cli-add-mode;
      list test {
        tailf:info
          "Configure SAA test";
        tailf:cli-recursive-delete;
        key "test-name";
        leaf test-name {
          type string {
            length "1..32";
          }
        }
        leaf accounting-policy {
          tailf:info
            "Configure an accounting-policy";
          tailf:cli-no-value-on-delete;
          type leafref {
            path "/ncs:devices/ncs:device/ncs:config/alu:log/accounting-policy/acct-policy-id" {
              tailf:xpath-root 3;
            }
          }
        }
        leaf continuous {
          tailf:cli-no-name-on-delete;
          tailf:info
            "repeat test indefinitely";
          type empty;
        }
        leaf description {
          tailf:cli-no-value-on-delete;
          tailf:info
            "Description for this SAA test";
          type string {
            length "1..80";
          }
        }
        container jitter-event {
          tailf:info
            "Configure jitter event threshold";
          tailf:cli-compact-syntax;
          leaf rising-threshold {
            tailf:cli-no-name-on-delete;
            tailf:cli-no-value-on-delete;
            type uint32 {
              range "0..2147483647";
            }
          }
          leaf falling-threshold {
            tailf:cli-no-name-on-delete;
            tailf:cli-no-value-on-delete;
            type uint32 {
              range "0..2147483647";
            }
          }
        }
        container latency-event {
          tailf:info
            "Configure latency event threshold";
          tailf:cli-compact-syntax;
          leaf rising-threshold {
            tailf:cli-no-name-on-delete;
            tailf:cli-no-value-on-delete;
            type uint32 {
              range "0..2147483647";
            }
          }
          leaf falling-threshold {
            tailf:cli-no-name-on-delete;
            tailf:cli-no-value-on-delete;
            type uint32 {
              range "0..2147483647";
            }
          }
        }
        container loss-event {
          tailf:info
            "Configure loss event threshold";
          tailf:cli-compact-syntax;
          leaf rising-threshold {
            tailf:cli-no-name-on-delete;
            tailf:cli-no-value-on-delete;
            type uint32 {
              range "0..2147483647";
            }
          }
          leaf falling-threshold {
            tailf:cli-no-name-on-delete;
            tailf:cli-no-value-on-delete;
            type uint32 {
              range "0..2147483647";
            }
          }
        }
        container type {
          tailf:cli-add-mode;
          tailf:info
            "Configure type of SAA test";
          container cpe-ping {
            tailf:cli-compact-syntax;
            tailf:info
              "Configure CPE ping test";
            leaf service {
              tailf:cli-no-name-on-delete;
              tailf:cli-no-value-on-delete;
              type union {
                type uint32 {
                  range "1..2147483647";
                }
                type string {
                  length "1..64";
                }
              }
            }
            leaf destination {
              tailf:cli-no-name-on-delete;
              tailf:cli-no-value-on-delete;
              type inet:ipv4-address;
            }
            leaf source {
              tailf:cli-no-name-on-delete;
              tailf:cli-no-value-on-delete;
              type inet:ipv4-address;
            }
            leaf source-mac {
              tailf:cli-no-name-on-delete;
              tailf:cli-no-value-on-delete;
              type ieee-mac;
            }
            leaf fc {
              tailf:cli-no-name-on-delete;
              tailf:cli-no-value-on-delete;
              type enumeration {
                enum "be";
                enum "l2";
                enum "af";
                enum "l1";
                enum "h2";
                enum "ef";
                enum "h1";
                enum "nc";
              }
              default "be";
            }
            leaf profile {
              tailf:cli-no-name-on-delete;
              tailf:cli-no-value-on-delete;
              type enumeration {
                enum "in";
                enum "out";
              }
              default "out";
            }
            leaf ttl {
              tailf:cli-no-name-on-delete;
              tailf:cli-no-value-on-delete;
              type uint8 {
                range "1..255";
              }
            }
            leaf count {
              tailf:cli-no-name-on-delete;
              tailf:cli-no-value-on-delete;
              type uint8 {
                range "1..100";
              }
            }
            leaf send-control {
              tailf:cli-no-name-on-delete;
              type empty;
            }
            leaf return-control {
              tailf:cli-no-name-on-delete;
              type empty;
            }
            leaf interval {
              tailf:cli-no-name-on-delete;
              tailf:cli-no-value-on-delete;
              type uint8 {
                range "1..10";
              }
            }
          }
          container dns {
            tailf:info
              "Configure DNS name resolution test";
            tailf:cli-compact-syntax;
            leaf target-addr {
              tailf:cli-no-name-on-delete;
              tailf:cli-no-value-on-delete;
              type string {
                length "1..255";
              }
            }
            leaf name-server {
              tailf:cli-no-name-on-delete;
              tailf:cli-no-value-on-delete;
              type union {
                type inet:ipv4-address;
                type inet:ipv6-address;
              }
            }
            leaf source {
              tailf:cli-no-name-on-delete;
              tailf:cli-no-value-on-delete;
              type union {
                type inet:ipv4-address;
                type inet:ipv6-address;
              }
            }
            leaf count {
              tailf:cli-no-name-on-delete;
              tailf:cli-no-value-on-delete;
              type uint8 {
                range "1..100";
              }
              default "1";
            }
            leaf timeout {
              tailf:cli-no-name-on-delete;
              tailf:cli-no-value-on-delete;
              type uint8 {
                range "1..120";
              }
              default "5";
            }
            leaf interval {
              tailf:cli-no-name-on-delete;
              tailf:cli-no-value-on-delete;
              type uint8 {
                range "1..10";
              }
              default "1";
            }
            leaf record-type {
              tailf:cli-no-name-on-delete;
              tailf:cli-no-value-on-delete;
              type enumeration {
                enum "ipv4-a-record";
                enum "ipv6-aaaa-record";
              }
            }
          }
          container eth-cfm-two-way-delay {
            tailf:info
              "Configure Ethernet Connectivity Fault Management two way delay test";
            tailf:cli-compact-syntax;
            leaf mac-address {
              tailf:cli-no-value-on-delete;
              tailf:cli-drop-node-name;
              type ieee-mac;
            }
            leaf mep {
              tailf:cli-no-value-on-delete;
              tailf:cli-no-name-on-delete;
              type uint16 {
                range "1..8191";
              }
            }
            leaf domain {
              tailf:cli-no-value-on-delete;
              tailf:cli-no-name-on-delete;
              type uint32 {
                range "1..4294967295";
              }
            }
            leaf association {
              tailf:cli-no-value-on-delete;
              tailf:cli-no-name-on-delete;
              type uint32 {
                range "1..4294967295";
              }
            }
            leaf fc {
              tailf:cli-no-value-on-delete;
              tailf:cli-no-name-on-delete;
              type enumeration {
                enum "be";
                enum "l2";
                enum "af";
                enum "l1";
                enum "h2";
                enum "ef";
                enum "h1";
                enum "nc";
              }
              default "nc";
            }
            leaf profile {
              tailf:cli-no-value-on-delete;
              tailf:cli-no-name-on-delete;
              type enumeration {
                enum "in";
                enum "out";
              }
              default "in";
            }
            leaf count {
              tailf:cli-no-value-on-delete;
              tailf:cli-no-name-on-delete;
              type uint16 {
                range "1..1000";
              }
              default "1";
            }
            leaf timeout {
              tailf:cli-no-value-on-delete;
              tailf:cli-no-name-on-delete;
              type uint8 {
                range "1..10";
              }
              default "5";
            }
            leaf interval {
              tailf:cli-no-value-on-delete;
              tailf:cli-no-name-on-delete;
              type uint8 {
                range "1..10";
              }
              default "5";
            }
          }
          container lsp-ping {
            tailf:cli-compact-syntax;
            tailf:info
              "";
            leaf lsp-name {
              tailf:cli-drop-node-name;
              type string {
                length "1..64";
              }
            }
            leaf path {
              tailf:cli-no-name-on-delete;
              tailf:cli-no-value-on-delete;
              type string {
                length "1..32";
              }
            }
            leaf fc {
              tailf:cli-no-value-on-delete;
              tailf:cli-no-name-on-delete;
              type enumeration {
                enum "be";
                enum "l2";
                enum "af";
                enum "l1";
                enum "h2";
                enum "ef";
                enum "h1";
                enum "nc";
              }
              default "be";
            }
            leaf profile {
              tailf:cli-no-value-on-delete;
              tailf:cli-no-name-on-delete;
              type enumeration {
                enum "in";
                enum "out";
              }
              default "out";
            }
            leaf interval {
              tailf:cli-no-name-on-delete;
              tailf:cli-no-value-on-delete;
              type uint8 {
                range "1..10";
              }
              default "1";
            }
            leaf send-count {
              tailf:cli-no-name-on-delete;
              tailf:cli-no-value-on-delete;
              type uint8 {
                range "1..100";
              }
              default "1";
            }
            leaf size {
              type uint16 {
                range "1..9198";
              }
              default "1";
            }
            leaf src-ip-address {
              tailf:cli-no-name-on-delete;
              tailf:cli-no-value-on-delete;
              type union {
                type inet:ipv4-address;
                type inet:ipv6-address;
              }
            }
            leaf timeout {
              tailf:cli-no-name-on-delete;
              tailf:cli-no-value-on-delete;
              type uint8 {
                range "1..10";
              }
              default "5";
            }
            leaf ttl {
              tailf:cli-no-name-on-delete;
              tailf:cli-no-value-on-delete;
              type uint8 {
                range "1..255";
              }
              default "255";
            }
          }
          container sdp-ping {
            tailf:cli-compact-syntax;
            tailf:info
              "Configure SDP ping test";
            leaf orig-sdp-id {
              tailf:cli-drop-node-name;
              type uint16 {
                range "1..17407";
              }
            }
            leaf resp-sdp {
              tailf:cli-no-name-on-delete;
              tailf:cli-no-value-on-delete;
              type uint16 {
                range "1..17407";
              }
            }
            leaf fc {
              tailf:cli-no-value-on-delete;
              tailf:cli-no-name-on-delete;
              type enumeration {
                enum "be";
                enum "l2";
                enum "af";
                enum "l1";
                enum "h2";
                enum "ef";
                enum "h1";
                enum "nc";
              }
              default "be";
            }
            leaf profile {
              tailf:cli-no-value-on-delete;
              tailf:cli-no-name-on-delete;
              type enumeration {
                enum "in";
                enum "out";
              }
              default "out";
            }
            leaf size {
              type uint16 {
                range "72..9198";
              }
              default "72";
            }
            leaf count {
              tailf:cli-no-name-on-delete;
              tailf:cli-no-value-on-delete;
              type uint8 {
                range "1..100";
              }
              default "1";
            }
            leaf timeout {
              tailf:cli-no-name-on-delete;
              tailf:cli-no-value-on-delete;
              type uint8 {
                range "1..10";
              }
              default "5";
            }
            leaf interval {
              tailf:cli-no-name-on-delete;
              tailf:cli-no-value-on-delete;
              type uint8 {
                range "1..10";
              }
              default "1";
            }
          }
          container vprn-ping {
            tailf:cli-compact-syntax;
            tailf:info
              "Configure VPRN ping test";
            leaf service-id {
              tailf:cli-drop-node-name;
              tailf:cli-no-value-on-delete;
              type uint32 {
                range "1..2147483647";
              }
            }
            leaf source {
              tailf:cli-no-name-on-delete;
              tailf:cli-no-value-on-delete;
              type union {
                type inet:ipv4-address;
                type inet:ipv6-address;
              }
            }
            leaf destination {
              tailf:cli-no-name-on-delete;
              tailf:cli-no-value-on-delete;
              type union {
                type inet:ipv4-address;
                type inet:ipv6-address;
              }
            }
            leaf fc {
              tailf:cli-no-name-on-delete;
              tailf:cli-no-value-on-delete;
              type enumeration {
                enum "be";
                enum "l2";
                enum "af";
                enum "l1";
                enum "h2";
                enum "ef";
                enum "h1";
                enum "nc";
              }
              default "be";
            }
            leaf profile {
              tailf:cli-no-name-on-delete;
              tailf:cli-no-value-on-delete;
              type enumeration {
                enum "in";
                enum "out";
              }
              default "out";
            }
            leaf size {
              tailf:cli-no-name-on-delete;
              tailf:cli-no-value-on-delete;
              type uint16 {
                range "1..9198";
              }
              default "1";
            }
            leaf ttl {
              tailf:cli-no-name-on-delete;
              tailf:cli-no-value-on-delete;
              type uint8 {
                range "1..255";
              }
            }
            leaf count {
              tailf:cli-no-name-on-delete;
              tailf:cli-no-value-on-delete;
              type uint8 {
                range "1..100";
              }
            }
            leaf return-control {
              tailf:cli-no-name-on-delete;
              type empty;
            }
            leaf timeout {
              tailf:cli-no-name-on-delete;
              tailf:cli-no-value-on-delete;
              type uint8 {
                range "1..100";
              }
            }
            leaf interval {
              tailf:cli-no-name-on-delete;
              tailf:cli-no-value-on-delete;
              type uint8 {
                range "1..10";
              }
            }
          }
        }
        container trap-gen {
          tailf:cli-add-mode;
          tailf:info
            "Configure trap generation for the SAA test";
          leaf probe-fail-enable {
            tailf:info
              "enable trap generation on ping probe failure";
            type empty;
          }
          leaf probe-fail-threshold {
            tailf:info
              "Configure threshold for trap generation on ping probe failure";
            tailf:cli-no-value-on-delete;
            type uint8 {
              range "0..15";
            }
          }
          leaf test-completion-enable {
            tailf:info
              "enable trap generation on test completion";
            type empty;
          }
          leaf test-fail-enable {
            tailf:info
              "enable trap generation on test failure";
            type empty;
          }
          leaf test-fail-threshold {
            tailf:info
              "configure threshold for trap generation on test failure";
            tailf:cli-no-value-on-delete;
            type uint8 {
              range "0..15";
            }
          }
        }
        leaf shutdown {
          tailf:info
            "Administratively enable/disable the mirror source";
          tailf:cli-boolean-no;
          default "true";
          type boolean;
        }
      }
    }
    container subscriber-mgmt {
      tailf:ncs-device-type "cli-ned";
      tailf:display-when "not(../../ncs:module) or ../../ncs:module[ncs:name='tailf-ned-alu-sr']";
      tailf:info
        "Configure subscriber management";
      tailf:cli-add-mode;
      list authentication-policy {
        tailf:info
          "Configure a subscriber authentication policy";
        tailf:cli-recursive-delete;
        tailf:cli-embed-no-on-delete;
        key "name";
        leaf name {
          type string;
        }
        leaf description {
          tailf:info
            "Description for authentication policy";
          tailf:cli-no-value-on-delete;
          type string;
        }
        container password {
          tailf:info
            "Configure the password used in the RADIUS request";
          tailf:cli-compact-syntax;
          tailf:cli-sequence-commands {
            tailf:cli-reset-siblings;
          }
          leaf pw {
            tailf:cli-drop-node-name;
            tailf:cli-no-value-on-delete;
            type string;
          }
          leaf hashing-scheme {
            tailf:cli-drop-node-name;
            tailf:cli-no-value-on-delete;
            type enumeration {
              enum "hash";
              enum "hash2";
            }
          }
        }
      }
      list sla-profile {
        tailf:info
          "Configure an SLA profile";
        tailf:cli-recursive-delete;
        tailf:cli-embed-no-on-delete;
        key "sla-profile-name";
        leaf sla-profile-name {
          type string;
        }
        leaf description {
          tailf:info
            "Description for this SLA profile";
          tailf:cli-no-value-on-delete;
          type string;
        }
        container ingress {
          tailf:info
            "Configure ingress parameters";
          tailf:cli-add-mode;
          list qos {
            tailf:info
              "Apply an ingress qos policy";
            tailf:cli-embed-no-on-delete;
            key "id";
            leaf id {
              type uint32;
            }
            leaf multipoint-shared {
              tailf:cli-hide-in-submode;
              type empty;
            }
          }
          leaf ip-filter {
            tailf:info
              "Configure an ip-filter";
            tailf:cli-no-value-on-delete;
            tailf:non-strict-leafref {
              path "/ncs:devices/ncs:device/ncs:config/alu:filter/ip-filter/ip-filter-name" {
                tailf:xpath-root 3;
              }
            }
            type string;
          }
          leaf ipv6-filter {
            tailf:info
              "Configure an ipv6-filter";
            tailf:cli-no-value-on-delete;
            tailf:non-strict-leafref {
              path "/ncs:devices/ncs:device/ncs:config/alu:filter/ipv6-filter/ip-filter-name" {
                tailf:xpath-root 3;
              }
            }
            type string;
          }
          leaf qos-marking-from-sap {
            tailf:info
              "QoS marking from SAP";
            tailf:cli-boolean-no;
            type boolean;
          }
        }
        container egress {
          tailf:info
            "Configure egress parameters";
          tailf:cli-add-mode;
          list qos {
            tailf:info
              "Apply an egress qos policy";
            tailf:cli-embed-no-on-delete;
            key "id";
            leaf id {
              type uint32;
            }
            leaf multipoint-shared {
              tailf:cli-hide-in-submode;
              tailf:cli-no-name-on-delete;
              type empty;
            }
          }
          leaf ip-filter {
            tailf:info
              "Configure an ip-filter";
            tailf:cli-no-value-on-delete;
            tailf:non-strict-leafref {
              path "/ncs:devices/ncs:device/ncs:config/alu:filter/ip-filter/ip-filter-name" {
                tailf:xpath-root 3;
              }
            }
            type string;
          }
          leaf ipv6-filter {
            tailf:info
              "Configure an ipv6-filter";
            tailf:cli-no-value-on-delete;
            tailf:non-strict-leafref {
              path "/ncs:devices/ncs:device/ncs:config/alu:filter/ipv6-filter/ip-filter-name" {
                tailf:xpath-root 3;
              }
            }
            type string;
          }
          leaf qos-marking-from-sap {
            tailf:info
              "Define the sap-egress qos-policy from which the egress qos marking rules are taken";
            tailf:cli-boolean-no;
            type boolean;
          }
        }
      }
      list sub-profile {
        tailf:info
          "Configure a subscriber profile";
        tailf:cli-recursive-delete;
        tailf:cli-embed-no-on-delete;
        key "sub-profile-name";
        leaf sub-profile-name {
          type string;
        }
        leaf description {
          tailf:info
            "Description for this subscriber profile";
          tailf:cli-no-value-on-delete;
          type string;
        }
        leaf accounting-policy {
          tailf:info
            "Configure accounting-policy to be used";
          tailf:cli-no-value-on-delete;
          type uint16;
        }
        leaf collect-stats {
          tailf:info
            "Enable/disable statistics collection";
          type empty;
        }
      }
    }
    container debug {
      tailf:ncs-device-type "cli-ned";
      tailf:display-when "not(../../ncs:module) or ../../ncs:module[ncs:name='tailf-ned-alu-sr']";
      tailf:info
        "Enable/disable debugging and specify debug options";
      tailf:cli-add-mode;
      list mirror-source {
        tailf:info
          "Configure a mirror source";
        tailf:cli-embed-no-on-delete;
        key "service-id";
        leaf service-id {
          type leafref {
            path "/ncs:devices/ncs:device/ncs:config/alu:mirror/mirror-dest/service-id" {
              tailf:xpath-root 3;
            }
          }
        }
        list ingress-label {
          tailf:info
            "Configure mirroring of ingress MPLS label to a mirror dest";
          tailf:cli-embed-no-on-delete;
          tailf:cli-compact-syntax;
          tailf:cli-suppress-mode;
          key "label";
          max-elements 8;
          leaf label {
            type uint32 {
              range "0..1048575";
            }
          }
        }
        list ip-filter {
          tailf:info
            "Configure mirroring for an IP filter to a mirror dest";
          tailf:cli-embed-no-on-delete;
          tailf:cli-compact-syntax;
          tailf:cli-suppress-mode;
          key "ip-filter-name";
          leaf ip-filter-name {
            tailf:non-strict-leafref {
              path "/ncs:devices/ncs:device/ncs:config/alu:filter/ip-filter/ip-filter-name" {
                tailf:xpath-root 3;
              }
            }
            type string;
          }
          list entry {
            tailf:cli-suppress-mode;
            key "id";
            max-elements 8;
            leaf id {
              type uint16 {
                range "1..65535";
              }
            }
          }
        }
        list mac-filter {
          tailf:info
            "Configure mirroring matching a mac filter to a mirror dest";
          tailf:cli-embed-no-on-delete;
          tailf:cli-compact-syntax;
          tailf:cli-suppress-mode;
          key "mac-filter-name";
          leaf mac-filter-name {
            tailf:non-strict-leafref {
              path "/ncs:devices/ncs:device/ncs:config/alu:filter/mac-filter/mac-filter-name" {
                tailf:xpath-root 3;
              }
            }
            type string;
          }
          list entry {
            tailf:cli-suppress-mode;
            key "id";
            max-elements 8;
            leaf id {
              type uint16 {
                range "1..65535";
              }
            }
          }
        }
        list port {
          tailf:info
            "Associate a port with a mirror source";
          tailf:cli-embed-no-on-delete;
          tailf:cli-compact-syntax;
          tailf:cli-suppress-mode;
          key "port-id";
          leaf lag {
            type empty;
          }
          leaf port-id {
            type string;
          }
          leaf ingress {
            type empty;
          }
          leaf egress {
            type empty;
          }
        }
        list sap {
          tailf:info
            "Associate a SAP with a mirror-source";
          tailf:cli-embed-no-on-delete;
          tailf:cli-compact-syntax;
          tailf:cli-suppress-mode;
          key "sap-id";
          leaf sap-id {
            type string;
          }
          leaf ingress {
            type empty;
          }
          leaf egress {
            type empty;
          }
        }
        list subscriber {
          tailf:info
            "Add hosts of a subscriber to mirroring service";
          tailf:cli-embed-no-on-delete;
          tailf:cli-compact-syntax;
          tailf:cli-suppress-mode;
          key "sub-ident-string";
          leaf sub-ident-string {
            type string;
          }
          leaf sap {
            type string;
          }
          leaf ip {
            type inet:ipv4-address;
          }
          leaf mac {
            type ieee-mac;
          }
          leaf sla-profile-name {
            type string;
          }
          leaf fc {
            type enumeration {
              enum "fc";
              enum "be";
              enum "l2";
              enum "af";
              enum "l1";
              enum "h2";
              enum "ef";
              enum "h1";
              enum "nc";
            }
          }
          leaf ingress {
            type empty;
          }
          leaf egress {
            type empty;
          }
        }
        leaf shutdown {
          tailf:info
            " Administratively enable/disable the mirror source";
          tailf:cli-boolean-no;
          default "true";
          type boolean;
        }
      }
    }
    container commands {
      tailf:ncs-device-type "cli-ned";
      tailf:display-when "not(../../ncs:module) or ../../ncs:module[ncs:name='tailf-ned-alu-sr']";
      tailf:cli-drop-node-name;
      tailf:action native-cmd {
        tailf:actionpoint ncsproxy {
          tailf:internal;
        }
        tailf:info
          "Execute a native command from the NCS CLI";
        // NCS drop tailf:actionpoint
        input {
          leaf command-string {
            tailf:cli-drop-node-name;
            type string;
          }
        }
        output {
          leaf result {
            type string;
          }
        }
      }
    }
  }
  augment "/ncs:devices/ncs:template/ncs:ned-id/ncs:config" {
    list card {
      // NCS patched for predictable order
      ordered-by user;
      key "slot-number";
      leaf slot-number {
        type string;
      }
      leaf card-type {
        type string;
      }
      leaf fail-on-error {
        type empty;
      }
      list mda {
        // NCS patched for predictable order
        ordered-by user;
        key "mda-slot";
        leaf mda-slot {
          type string;
        }
        leaf mda-type {
          type string;
        }
        container access {
          container ingress {
            leaf fabric-policy {
              type string;
            }
          }
        }
        container network {
          container ingress {
            leaf fabric-policy {
              type string;
            }
            container pool {
              leaf slope-policy {
                type string;
              }
            }
            leaf queue-policy {
              type string;
            }
          }
        }
        leaf shutdown {
          // NCS drop default statement
          type string;
        }
      }
      list fp {
        // NCS patched for predictable order
        ordered-by user;
        key "id";
        leaf id {
          type string;
        }
        container ingress {
          container mcast-path-management {
            leaf bandwidth-policy {
              type string;
            }
            leaf shutdown {
              // NCS drop default statement
              type string;
            }
          }
        }
      }
      leaf shutdown {
        // NCS drop default statement
        type string;
      }
    }
    container cflowd {
      presence "present";
      leaf active-timeout {
        type string;
      }
      leaf cache-size {
        type string;
      }
      list collector {
        // NCS patched for predictable order
        ordered-by user;
        key "collector-id";
        leaf collector-id {
          type string;
        }
        leaf version {
          type string;
        }
        leaf description {
          type string;
        }
        leaf template-set {
          // NCS drop when statement
          type string;
        }
        leaf autonomous-system-type {
          // NCS drop when statement
          type string;
        }
        leaf shutdown {
          type empty;
        }
      }
      leaf export-mode {
        type string;
        // NCS drop default statement
      }
      leaf inactive-timeout {
        type string;
      }
      leaf overflow {
        type string;
      }
      leaf rate {
        type string;
      }
      leaf template-retransmit {
        type string;
      }
      leaf shutdown {
        type empty;
      }
    }
    container ipsec {
      list ike-policy {
        // NCS patched for predictable order
        ordered-by user;
        key "ike-policy-id";
        leaf ike-policy-id {
          type string;
        }
        leaf auth-algorithm {
          type string;
        }
        leaf auth-method {
          type string;
        }
        leaf auto-eap-method {
          type string;
        }
        leaf auto-eap-own-method {
          type string;
        }
        leaf description {
          type string;
        }
        leaf dh-group {
          type string;
        }
        container dpd {
          presence "present";
          leaf interval {
            type string;
          }
          leaf max-retries {
            type string;
          }
          leaf reply-only {
            type empty;
          }
        }
        leaf encryption-algorithm {
          type string;
        }
        leaf ike-mode {
          type string;
        }
        leaf ike-version {
          type string;
        }
        leaf ipsec-lifetime {
          type string;
        }
        leaf isakmp-lifetime {
          type string;
        }
        leaf match-peer-id-to-cert {
          type empty;
        }
        container nat-traversal {
          presence "present";
          leaf force {
            type empty;
          }
          leaf keep-alive-interval {
            type string;
          }
          leaf force-keep-alive {
            type empty;
          }
        }
        leaf own-auth-method {
          type string;
        }
        container pfs {
          presence "present";
          leaf dh-group {
            type string;
          }
        }
      }
      list ipsec-transform {
        // NCS patched for predictable order
        ordered-by user;
        key "transform-id";
        leaf transform-id {
          type string;
        }
        leaf esp-auth-algorithm {
          type string;
        }
        leaf esp-encryption-algorithm {
          type string;
        }
      }
    }
    container isa {
      list tunnel-group {
        // NCS patched for predictable order
        ordered-by user;
        key "tunnel-group-id";
        leaf tunnel-group-id {
          type string;
        }
        leaf primary {
          type string;
        }
        leaf shutdown {
          // NCS drop default statement
          type string;
        }
      }
    }
    list lag {
      // NCS patched for predictable order
      ordered-by user;
      // NCS drop tailf-common:cli-diff-dependency statement
      key "id";
      leaf id {
        type string;
      }
      leaf description {
        type string;
      }
      leaf mode {
        type string;
      }
      leaf encap-type {
        type string;
      }
      list port {
        // NCS patched for predictable order
        ordered-by user;
        key "id";
        leaf id {
          type string;
        }
        leaf priority {
          type string;
        }
      }
      container port-threshold {
        leaf value {
          type string;
        }
        leaf action {
          type string;
        }
      }
      container lacp {
        leaf mode {
          type string;
        }
        leaf administrative-key {
          type string;
        }
        leaf system-id {
          type string;
        }
        leaf system-priority {
          type string;
        }
      }
      leaf shutdown {
        // NCS drop default statement
        type string;
      }
    }
    list port {
      // NCS patched for predictable order
      ordered-by user;
      key "port-id";
      leaf port-id {
        type string;
      }
      leaf description {
        type string;
      }
      container ethernet {
        leaf mode {
          // NCS drop tailf-common:cli-diff-dependency statement
          // NCS drop tailf-common:cli-diff-dependency statement
          type string;
        }
        container access {
          // NCS drop tailf-common:cli-diff-dependency statement
          leaf accounting-policy {
            type string;
          }
          leaf collect-stats {
            type empty;
          }
          container egress {
            leaf qos {
              type string;
            }
          }
        }
        container autonegotiate {
          presence "true";
          leaf limited {
            type empty;
          }
        }
        leaf dot1q-etype {
          type string;
        }
        leaf duplex {
          type string;
        }
        container efm-oam {
          leaf accept-remote-loopback {
            type empty;
          }
          container transmit-interval {
            leaf interval {
              type string;
            }
            leaf multiplier {
              type string;
            }
          }
        }
        leaf encap-type {
          type string;
        }
        leaf egress-rate {
          type string;
        }
        leaf egress-scheduler-policy {
          // NCS drop tailf-common:cli-diff-dependency statement
          type string;
        }
        container egress-scheduler-override {
          // NCS drop tailf-common:cli-diff-dependency statement
          list level {
            // NCS patched for predictable order
            ordered-by user;
            key "priority-level";
            leaf priority-level {
              type string;
            }
            leaf rate {
              type string;
            }
            leaf cir {
              type string;
            }
          }
          leaf max-rate {
            type string;
          }
        }
        container hold-time {
          leaf up {
            type string;
          }
          leaf down {
            type string;
          }
          leaf unit {
            type string;
          }
        }
        leaf ingress-rate {
          type string;
        }
        container lldp {
          list dest-mac {
            // NCS patched for predictable order
            ordered-by user;
            // NCS drop max-elements statement
            key "id";
            leaf id {
              type string;
            }
            leaf notification {
              type empty;
            }
            leaf admin-status {
              type string;
            }
            container tx-tlvs {
              leaf port-desc {
                type empty;
              }
              leaf sys-name {
                type empty;
              }
              leaf sys-desc {
                type empty;
              }
              leaf sys-cap {
                type empty;
              }
            }
            leaf tx-mgmt-address {
              type string;
            }
          }
        }
        leaf mac {
          type ncs_template_ieee-mac;
        }
        leaf mtu {
          type string;
        }
        container network {
          // NCS drop tailf-common:cli-diff-dependency statement
          leaf queue-policy {
            type string;
          }
          leaf scheduler-mode {
            type string;
          }
        }
      }
      container dwdm {
        container amplifier {
          leaf-list report-alarms {
            // NCS patched for predictable order
            ordered-by user;
            type string;
          }
        }
        leaf channel {
          type string;
        }
        container coherent {
          leaf target-power {
            type string;
          }
          leaf compatibility {
            type string;
          }
          container sweep {
            leaf start {
              type string;
            }
            leaf end {
              type string;
            }
          }
          leaf channel {
            type string;
          }
          leaf mode {
            type string;
          }
        }
        leaf rxdtv-adjust {
          type empty;
        }
        container tdcm {
          leaf channel {
            type string;
          }
          leaf dispersion {
            type string;
          }
          leaf mode {
            type string;
          }
          leaf-list report-alarms {
            // NCS patched for predictable order
            ordered-by user;
            type string;
          }
          container sweep {
            leaf start {
              type string;
            }
            leaf end {
              type string;
            }
          }
          leaf shutdown {
            // NCS drop default statement
            type string;
          }
        }
      }
      container modify-buffer-allocation-rate {
        leaf egr-percentage-of-rate {
          type string;
        }
        leaf ing-percentage-of-rate {
          type string;
        }
      }
      container multilink-bundle {
        leaf fragment-threshold {
          type string;
        }
        list member {
          // NCS patched for predictable order
          ordered-by user;
          key "id";
          leaf id {
            type string;
          }
        }
      }
      container network {
        container egress {
          container pool {
            leaf slope-policy {
              type string;
            }
          }
        }
      }
      container otu {
        leaf async-mapping {
          type empty;
        }
        leaf fec {
          type string;
        }
        leaf otu2-lan-data-rate {
          type string;
        }
        leaf-list report-alarms {
          // NCS patched for predictable order
          ordered-by user;
          type string;
        }
        leaf sd-threshold {
          type string;
        }
        leaf sf-sd-method {
          type string;
        }
        leaf sf-threshold {
          type string;
        }
      }
      container sonet-sdh {
        leaf clock-source {
          type string;
        }
        leaf framing {
          type string;
        }
        container group {
          leaf sonet-sdh-index {
            type string;
          }
          leaf payload {
            type string;
          }
        }
        container hold-time {
          leaf up {
            type string;
          }
          leaf down {
            type string;
          }
        }
        leaf loopback {
          type string;
        }
        list path {
          // NCS patched for predictable order
          ordered-by user;
          key "sonet-sdh-index";
          leaf sonet-sdh-index {
            type string;
          }
          leaf payload {
            type string;
          }
        }
        leaf report-alarm {
          type string;
        }
        container section-trace {
          choice a {
            leaf increment-z0 {
              type empty;
            }
            leaf byte {
              type string;
            }
            leaf string {
              type string;
            }
          }
        }
        leaf single-fiber {
          type empty;
        }
        leaf speed {
          type string;
        }
        leaf suppress-lo-alarm {
          type empty;
        }
        container threshold {
          leaf value {
            type string;
          }
          leaf rate {
            type string;
          }
        }
        leaf tx-dus {
          type empty;
        }
      }
      container tdm {
        leaf buildout {
          type string;
        }
        list ds1 {
          // NCS patched for predictable order
          ordered-by user;
          key "ds1-id";
          leaf ds1-id {
            type string;
          }
          container bert {
            leaf value {
              type string;
            }
            leaf duration {
              type string;
            }
          }
          leaf bit-error-insertion {
            type string;
          }
          list channel-group {
            // NCS patched for predictable order
            ordered-by user;
            // NCS drop max-elements statement
            key "id";
            leaf id {
              type string;
            }
            leaf clock-source {
              type string;
            }
            leaf encap-type {
              type string;
            }
            container ppp {
              leaf ber-sf-link-down {
                type empty;
              }
            }
            leaf timeslots {
              type string;
            }
            leaf shutdown {
              // NCS drop default statement
              type string;
            }
          }
          leaf clock-source {
            type string;
          }
          leaf framing {
            type string;
          }
          leaf invert-data {
            type empty;
          }
          leaf loopback {
            type string;
          }
          leaf remote-loop-respond {
            type empty;
          }
          leaf report-alarm {
            type string;
          }
          leaf signal-mode {
            type string;
          }
          container threshold {
            leaf value {
              type string;
            }
            leaf rate {
              type string;
            }
          }
          leaf shutdown {
            // NCS drop default statement
            type string;
          }
        }
        list ds3 {
          // NCS patched for predictable order
          ordered-by user;
          key "ds3-id";
          leaf ds3-id {
            type string;
          }
          container bert {
            leaf value {
              type string;
            }
          }
          leaf channelized {
            type string;
          }
          leaf clock-source {
            type string;
          }
          leaf encap-type {
            type string;
          }
          leaf shutdown {
            // NCS drop default statement
            type string;
          }
        }
        leaf lbo {
          type string;
        }
        leaf length {
          type string;
        }
      }
      leaf shutdown {
        // NCS drop default statement
        type string;
      }
    }
    container qos {
      list fabric-profile {
        // NCS patched for predictable order
        ordered-by user;
        key "policy-id";
        leaf policy-id {
          type string;
        }
        leaf mode {
          type string;
        }
        leaf aggregate-rate {
          type string;
        }
        leaf description {
          type string;
        }
        list dest-mda {
          // NCS patched for predictable order
          ordered-by user;
          key "id";
          leaf id {
            type string;
          }
          leaf rate {
            type string;
          }
        }
      }
      list network-queue {
        // NCS patched for predictable order
        ordered-by user;
        key "network-queue-name";
        leaf network-queue-name {
          type string;
        }
        leaf description {
          type string;
        }
        list queue {
          // NCS patched for predictable order
          ordered-by user;
          key "id";
          leaf id {
            type string;
          }
          leaf multipoint {
            type empty;
          }
          leaf queue-type {
            type string;
          }
          leaf mbs {
            // NCS drop default statement
            type string;
          }
          leaf cbs {
            type string;
          }
          leaf high-prio-only {
            // NCS drop default statement
            type string;
          }
          container rate {
            leaf percent {
              type string;
            }
            leaf cir {
              type string;
            }
          }
          container port-parent {
            presence "present";
            leaf weight {
              type string;
            }
            leaf level {
              type string;
            }
            leaf cir-weight {
              type string;
            }
            leaf cir-level {
              type string;
            }
          }
        }
        list fc {
          // NCS patched for predictable order
          ordered-by user;
          key "id";
          leaf id {
            type string;
          }
          leaf multicast-queue {
            type string;
          }
          leaf queue {
            type string;
          }
          container egress-hsmda {
            leaf queue {
              type string;
            }
          }
        }
      }
      container queue-group-templates {
        container egress {
          list queue-group {
            // NCS patched for predictable order
            ordered-by user;
            key "queue-group-name";
            uses ncs_template_queue-group-template-entry;
          }
        }
        container ingress {
          list queue-group {
            // NCS patched for predictable order
            ordered-by user;
            key "queue-group-name";
            uses ncs_template_queue-group-template-entry;
          }
        }
      }
      list scheduler-policy {
        // NCS patched for predictable order
        ordered-by user;
        key "scheduler-policy-name";
        leaf scheduler-policy-name {
          type string;
        }
        leaf description {
          type string;
        }
        leaf frame-based-accounting {
          type empty;
        }
        list tier {
          // NCS patched for predictable order
          ordered-by user;
          key "tier";
          leaf tier {
            type string;
          }
          list scheduler {
            // NCS patched for predictable order
            ordered-by user;
            key "scheduler-name";
            leaf scheduler-name {
              type string;
            }
            leaf description {
              type string;
            }
            container parent {
              presence "present";
              leaf scheduler-name {
                type string;
              }
              leaf weight {
                type string;
              }
              leaf level {
                type string;
              }
              leaf cir-weight {
                type string;
              }
              leaf cir-level {
                type string;
              }
            }
            container port-parent {
              presence "present";
              leaf weight {
                type string;
              }
              leaf level {
                type string;
              }
              leaf cir-weight {
                type string;
              }
              leaf cir-level {
                type string;
              }
            }
            container rate {
              presence "present";
              leaf pir-rate {
                // NCS drop mandatory statement
                type string;
              }
              leaf cir {
                type string;
              }
            }
            container mbs {
              leaf size {
                type string;
              }
              leaf unit {
                type string;
              }
            }
          }
        }
      }
      list shared-queue {
        // NCS patched for predictable order
        ordered-by user;
        key "policy-name";
        leaf policy-name {
          type string;
        }
        leaf description {
          type string;
        }
        container fc {
          presence "present";
          leaf fc-name {
            // NCS drop mandatory statement
            type string;
          }
          leaf broadcast-queue {
            type string;
          }
          leaf multicast-queue {
            type string;
          }
          leaf queue {
            type string;
          }
          leaf unknown-queue {
            type string;
          }
        }
        list queue {
          // NCS patched for predictable order
          ordered-by user;
          key "queue-id";
          leaf queue-id {
            type string;
          }
          leaf queue-type {
            type string;
          }
          leaf multipoint {
            type empty;
          }
          leaf cbs {
            type string;
          }
          leaf high-prio-only {
            type string;
          }
          leaf mbs {
            type string;
          }
          leaf pool {
            type string;
          }
          container rate {
            presence "present";
            leaf percent {
              // NCS drop mandatory statement
              type string;
            }
            leaf cir {
              type string;
            }
          }
        }
      }
      list mpls-lsp-exp-profile-map {
        // NCS patched for predictable order
        ordered-by user;
        key "policy-id";
        leaf policy-id {
          type string;
        }
        leaf description {
          type string;
        }
        container lsp-exp {
          leaf lsp-exp-value {
            type string;
          }
          leaf profile {
            type string;
          }
        }
      }
      list sap-egress {
        // NCS patched for predictable order
        ordered-by user;
        // NCS drop tailf-common:cli-diff-dependency statement
        key "policy-id";
        leaf policy-id {
          type string;
        }
        leaf policy-name {
          type string;
        }
        leaf description {
          type string;
        }
        list queue {
          // NCS patched for predictable order
          ordered-by user;
          key "queue-id";
          leaf queue-id {
            type string;
          }
          leaf queue-type {
            type string;
          }
          container adaptation-rule {
            leaf pir {
              type string;
            }
            leaf cir {
              type string;
            }
          }
          container parent {
            leaf scheduler-name {
              type string;
            }
            leaf weight {
              type string;
            }
            leaf level {
              type string;
            }
            leaf cir-weight {
              type string;
            }
            leaf cir-level {
              type string;
            }
          }
          container port-parent {
            leaf weight {
              type string;
            }
            leaf level {
              type string;
            }
            leaf cir-weight {
              type string;
            }
            leaf cir-level {
              type string;
            }
          }
          container rate {
            leaf pir-rate {
              type string;
            }
            leaf cir {
              type string;
            }
          }
          container cbs {
            leaf size {
              type string;
            }
          }
          container mbs {
            leaf size {
              type string;
            }
            leaf unit {
              type string;
            }
          }
          container burst-limit {
            leaf size {
              type string;
            }
            leaf unit {
              type string;
            }
          }
          container xp-specific {
            container wred-queue {
              leaf policy {
                type string;
              }
            }
            container packet-byte-offset {
              choice a {
                leaf add {
                  type string;
                }
                leaf subtract {
                  type string;
                }
              }
            }
          }
        }
        list fc {
          // NCS patched for predictable order
          ordered-by user;
          key "fc-name";
          leaf fc-name {
            type string;
          }
          leaf queue {
            type string;
          }
          container dot1p {
            choice dot1p-choice {
              case a {
                leaf dot1p-value {
                  type string;
                }
              }
              case b {
                leaf in-profile {
                  type string;
                }
                leaf out-profile {
                  type string;
                }
              }
            }
          }
        }
        container ip-criteria {
          uses ncs_template_ip-criteria-grouping;
        }
        container ipv6-criteria {
          uses ncs_template_ipv6-criteria-grouping;
        }
        list dscp {
          // NCS patched for predictable order
          ordered-by user;
          key "id";
          leaf id {
            type ncs_template_dscp-type;
          }
          leaf fc {
            type string;
          }
          leaf priority {
            type string;
          }
        }
      }
      list sap-ingress {
        // NCS patched for predictable order
        ordered-by user;
        // NCS drop tailf-common:cli-diff-dependency statement
        key "policy-id";
        leaf policy-id {
          type string;
        }
        leaf description {
          type string;
        }
        leaf policy-name {
          type string;
        }
        list meter {
          // NCS patched for predictable order
          ordered-by user;
          key "meter-id";
          uses ncs_template_meter-grouping;
        }
        container num-qos-classifiers {
          leaf num-resources {
            type string;
          }
          leaf keyword {
            type string;
          }
        }
        list prec {
          // NCS patched for predictable order
          ordered-by user;
          key "ip-prec-value";
          leaf ip-prec-value {
            type string;
          }
          leaf fc {
            type string;
          }
          leaf priority {
            type string;
          }
        }
        list queue {
          // NCS patched for predictable order
          ordered-by user;
          key "queue-id";
          leaf queue-id {
            type string;
          }
          leaf multipoint {
            type empty;
          }
          leaf queue-type {
            type string;
          }
          leaf queue-mode {
            type string;
          }
          container adaptation-rule {
            leaf pir {
              type string;
            }
            leaf cir {
              type string;
            }
          }
          container parent {
            leaf scheduler-name {
              type string;
            }
            leaf weight {
              type string;
            }
            leaf level {
              type string;
            }
            leaf cir-weight {
              type string;
            }
            leaf cir-level {
              type string;
            }
          }
          container cbs {
            leaf size {
              type string;
            }
          }
          container mbs {
            leaf size {
              type string;
            }
            leaf unit {
              type string;
            }
          }
          container rate {
            leaf pir-rate {
              type string;
            }
            leaf cir {
              type string;
            }
          }
        }
        list fc {
          // NCS patched for predictable order
          ordered-by user;
          key "fc-name";
          leaf fc-name {
            type string;
          }
          leaf queue {
            type string;
          }
          container broadcast-queue {
            leaf id {
              type string;
            }
            leaf group {
              type string;
            }
          }
          container multicast-queue {
            leaf id {
              type string;
            }
            leaf group {
              type string;
            }
          }
          container unknown-queue {
            leaf id {
              type string;
            }
            leaf group {
              type string;
            }
          }
          leaf broadcast-meter {
            type string;
          }
          leaf meter {
            type string;
          }
          leaf multicast-meter {
            type string;
          }
          leaf unknown-meter {
            type string;
          }
          container in-remark {
            choice remark-choice {
              leaf dscp {
                type ncs_template_dscp-type;
              }
              leaf prec {
                type string;
              }
            }
          }
          container out-remark {
            choice remark-choice {
              leaf dscp {
                type ncs_template_dscp-type;
              }
              leaf prec {
                type string;
              }
            }
          }
          container policer {
            leaf id {
              type string;
            }
            leaf fp-redirect-group {
              type string;
            }
          }
        }
        container ip-criteria {
          uses ncs_template_ip-criteria-grouping;
        }
        container ipv6-criteria {
          uses ncs_template_ipv6-criteria-grouping;
        }
        leaf default-fc {
          type string;
        }
        leaf default-priority {
          type string;
        }
        list dot1p {
          // NCS patched for predictable order
          ordered-by user;
          key "id";
          leaf id {
            type string;
          }
          leaf fc {
            type string;
          }
          leaf priority {
            type string;
          }
        }
        list dscp {
          // NCS patched for predictable order
          ordered-by user;
          key "id";
          leaf id {
            type ncs_template_dscp-type;
          }
          leaf fc {
            type string;
          }
          leaf priority {
            type string;
          }
        }
        list policer {
          // NCS patched for predictable order
          ordered-by user;
          key "id";
          leaf id {
            type string;
          }
          container rate {
            leaf pir {
              type string;
            }
            leaf cir {
              type string;
            }
          }
          container cbs {
            leaf size {
              type string;
            }
          }
          container mbs {
            leaf size {
              type string;
            }
            leaf unit {
              type string;
            }
          }
        }
      }
      list network {
        // NCS patched for predictable order
        ordered-by user;
        key "id";
        leaf id {
          type string;
        }
        leaf network-policy-type {
          type string;
        }
        leaf description {
          type string;
        }
        container ingress {
          list dscp {
            // NCS patched for predictable order
            ordered-by user;
            key "id";
            leaf id {
              type ncs_template_dscp-type;
            }
            leaf fc {
              type string;
            }
            leaf profile {
              type string;
            }
          }
          list lsp-exp {
            // NCS patched for predictable order
            ordered-by user;
            key "id";
            leaf id {
              type string;
            }
            leaf fc {
              type string;
            }
            leaf profile {
              type string;
            }
          }
          container default-action {
            leaf fc {
              type string;
            }
            leaf profile {
              type string;
            }
          }
          list meter {
            // NCS patched for predictable order
            ordered-by user;
            key "meter-id";
            uses ncs_template_meter-grouping;
          }
          leaf mpls-lsp-exp-profile {
            type string;
          }
          list fc {
            // NCS patched for predictable order
            ordered-by user;
            key "class";
            leaf class {
              type string;
            }
            leaf meter {
              type string;
            }
            leaf multicast-meter {
              type string;
            }
          }
        }
        container egress {
          list fc {
            // NCS patched for predictable order
            ordered-by user;
            key "id";
            leaf id {
              type string;
            }
            leaf dscp-in-profile {
              type ncs_template_dscp-type;
            }
            leaf dscp-out-profile {
              type ncs_template_dscp-type;
            }
            leaf lsp-exp-in-profile {
              type string;
            }
            leaf lsp-exp-out-profile {
              type string;
            }
            leaf dot1p-in-profile {
              type string;
            }
            leaf dot1p-out-profile {
              type string;
            }
          }
          container remarking {
            presence "true";
            leaf force {
              type empty;
            }
          }
          container prec {
            leaf prec-value {
              type string;
            }
            leaf fc {
              type string;
            }
            leaf profile {
              type string;
            }
          }
          list dscp {
            // NCS patched for predictable order
            ordered-by user;
            key "id";
            leaf id {
              type ncs_template_dscp-type;
            }
            leaf fc {
              type string;
            }
            leaf profile {
              type string;
            }
          }
        }
      }
      list slope-policy {
        // NCS patched for predictable order
        ordered-by user;
        key "name";
        leaf name {
          type string;
        }
        leaf description {
          type string;
        }
        container high-slope {
          leaf start-avg {
            type string;
          }
          leaf max-avg {
            type string;
          }
          leaf max-prob {
            type string;
          }
          leaf shutdown {
            // NCS drop default statement
            type string;
          }
        }
        container low-slope {
          leaf start-avg {
            type string;
          }
          leaf max-avg {
            type string;
          }
          leaf max-prob {
            type string;
          }
          leaf shutdown {
            // NCS drop default statement
            type string;
          }
        }
      }
      list port-scheduler-policy {
        // NCS patched for predictable order
        ordered-by user;
        key "name";
        leaf name {
          type string;
        }
        leaf description {
          type string;
        }
        list level {
          // NCS patched for predictable order
          ordered-by user;
          key "priority-level";
          leaf priority-level {
            type string;
          }
          leaf rate {
            type string;
          }
          leaf cir {
            type string;
          }
        }
        leaf max-rate {
          type string;
        }
        container orphan-override {
          leaf level {
            type string;
          }
        }
      }
      list policer-control-policy {
        // NCS patched for predictable order
        ordered-by user;
        key "name";
        leaf name {
          type string;
        }
        leaf description {
          type string;
        }
        container root {
          leaf max-rate {
            type string;
          }
        }
        container priority-mbs-thresholds {
          container min-thresh-separation {
            leaf size {
              type string;
            }
            leaf unit {
              type string;
            }
          }
          list priority {
            // NCS patched for predictable order
            ordered-by user;
            key "level";
            leaf level {
              type string;
            }
            container mbs-contribution {
              leaf size {
                type string;
              }
              leaf unit {
                type string;
              }
              leaf fixed {
                type empty;
              }
            }
          }
        }
      }
    }
    container eth-cfm {
      list domain {
        // NCS patched for predictable order
        ordered-by user;
        key "id";
        leaf id {
          type string;
        }
        leaf format {
          type string;
        }
        leaf level {
          type string;
        }
        leaf name {
          type string;
        }
        list association {
          // NCS patched for predictable order
          ordered-by user;
          key "ma-index";
          leaf ma-index {
            type string;
          }
          leaf format {
            type string;
          }
          leaf name {
            type string;
          }
          container ccm-hold-time {
            leaf down {
              type string;
            }
          }
          leaf ccm-interval {
            type string;
          }
          container remote-mepid {
            leaf mep-id {
              type string;
            }
            leaf remote-mac {
              type string;
            }
          }
          list bridge-identifier {
            // NCS patched for predictable order
            ordered-by user;
            key "id";
            leaf id {
              type string;
            }
            leaf mhf-creation {
              type string;
            }
            leaf vlan {
              type string;
            }
          }
        }
      }
    }
    container log {
      list file-id {
        // NCS patched for predictable order
        ordered-by user;
        key "id";
        leaf id {
          type string;
        }
        leaf description {
          type string;
        }
        leaf-list location {
          // NCS patched for predictable order
          ordered-by user;
          type string;
        }
        container rollover {
          leaf id {
            type string;
          }
          leaf retention {
            type string;
          }
        }
      }
      list accounting-policy {
        // NCS patched for predictable order
        ordered-by user;
        key "acct-policy-id";
        leaf acct-policy-id {
          type string;
        }
        leaf collection-interval {
          type string;
        }
        leaf description {
          type string;
        }
        leaf record {
          type string;
        }
        container to {
          leaf destination {
            type string;
          }
          leaf log-file-id {
            // NCS drop when statement
            type string;
          }
        }
        leaf shutdown {
          // NCS drop default statement
          type string;
        }
      }
      list event-control {
        // NCS patched for predictable order
        ordered-by user;
        key "name";
        leaf name {
          type string;
        }
        leaf year {
          type string;
        }
        leaf generate {
          type empty;
        }
        leaf throttle {
          type empty;
        }
      }
      list filter {
        // NCS patched for predictable order
        ordered-by user;
        key "filter-id";
        leaf filter-id {
          type string;
        }
        leaf default-action {
          type string;
        }
        leaf description {
          type string;
        }
        list entry {
          // NCS patched for predictable order
          ordered-by user;
          key "entry-id";
          leaf entry-id {
            type string;
          }
          leaf action {
            type string;
          }
          leaf description {
            type string;
          }
          container match {
            container application {
              leaf rule {
                type string;
              }
              leaf application-id {
                type string;
              }
            }
            container message {
              leaf rule {
                type string;
              }
              leaf pattern {
                type string;
              }
              leaf regexp {
                type empty;
              }
            }
            container number {
              leaf rule {
                type string;
              }
              leaf event-id {
                type string;
              }
            }
            container router {
              leaf rule {
                type string;
              }
              leaf router-instance {
                type string;
              }
              leaf regexp {
                type empty;
              }
            }
            container severity {
              leaf rule {
                type string;
              }
              leaf severity-level {
                type string;
              }
            }
            container subject {
              leaf rule {
                type string;
              }
              leaf subject {
                type string;
              }
              leaf regexp {
                type empty;
              }
            }
          }
        }
      }
      list snmp-trap-group {
        // NCS patched for predictable order
        ordered-by user;
        key "id";
        leaf id {
          type string;
        }
        leaf-list trap-target {
          // NCS patched for predictable order
          ordered-by user;
          type string;
        }
        leaf description {
          type string;
        }
      }
      list log-id {
        // NCS patched for predictable order
        ordered-by user;
        key "id";
        leaf id {
          type string;
        }
        leaf description {
          type string;
        }
        leaf filter {
          type string;
        }
        leaf-list from {
          // NCS patched for predictable order
          ordered-by user;
          type string;
        }
        leaf time-format {
          type string;
        }
        container to {
          choice choice {
            case file {
              leaf file {
                type string;
              }
            }
            case syslog {
              leaf syslog {
                type string;
              }
            }
            case console {
              leaf console {
                type empty;
              }
            }
            case snmp {
              container snmp {
                presence "true";
                leaf size {
                  type string;
                }
              }
            }
            case memory {
              leaf memory {
                type empty;
              }
            }
            case session {
              leaf session {
                type string;
              }
            }
          }
        }
        leaf shutdown {
          // NCS drop default statement
          type string;
        }
      }
      list syslog {
        // NCS patched for predictable order
        ordered-by user;
        key "id";
        leaf id {
          type string;
        }
        leaf address {
          type string;
        }
        leaf description {
          type string;
        }
        leaf facility {
          type string;
        }
        leaf log-prefix {
          type string;
        }
        leaf level {
          type string;
        }
      }
    }
    container service {
      // NCS drop tailf-common:cli-diff-dependency statement
      list customer {
        // NCS patched for predictable order
        ordered-by user;
        key "customer-id";
        leaf customer-id {
          type string;
        }
        leaf contact {
          type string;
        }
        leaf description {
          type string;
        }
        list multi-service-site {
          // NCS patched for predictable order
          ordered-by user;
          // NCS drop tailf-common:cli-diff-dependency statement
          // NCS drop tailf-common:cli-diff-dependency statement
          key "customer-site-name";
          leaf customer-site-name {
            type string;
          }
          container assignment {
            choice choice {
              leaf port {
                type string;
              }
              leaf card {
                type string;
              }
            }
          }
          leaf description {
            type string;
          }
          container egress {
            container agg-rate-limit {
              presence "present";
              leaf agg-rate {
                // NCS drop mandatory statement
                type string;
              }
              leaf queue-frame-based-accounting {
                type empty;
              }
            }
            leaf policer-control-policy {
              type string;
            }
            leaf scheduler-policy {
              type string;
            }
            container scheduler-override {
              list scheduler {
                // NCS patched for predictable order
                ordered-by user;
                key "scheduler-name";
                leaf scheduler-name {
                  type string;
                }
                container rate {
                  leaf pir-rate {
                    type string;
                  }
                  leaf cir {
                    type string;
                  }
                }
              }
            }
          }
          container ingress {
            leaf policer-control-policy {
              type string;
            }
            leaf scheduler-policy {
              type string;
            }
            container scheduler-override {
              list scheduler {
                // NCS patched for predictable order
                ordered-by user;
                key "scheduler-name";
                leaf scheduler-name {
                  type string;
                }
                container rate {
                  presence "present";
                  leaf pir-rate {
                    // NCS drop mandatory statement
                    type string;
                  }
                  leaf cir {
                    type string;
                  }
                }
              }
            }
          }
          leaf tod-suite {
            type string;
          }
        }
        leaf phone {
          type string;
        }
      }
      list sdp {
        // NCS patched for predictable order
        ordered-by user;
        key "sdp-id";
        leaf sdp-id {
          type string;
        }
        leaf accounting-policy {
          type string;
        }
        leaf adv-mtu-override {
          type empty;
        }
        leaf bgp-tunnel {
          type empty;
        }
        container binding {
          leaf port {
            type string;
          }
          list pw-port {
            // NCS patched for predictable order
            ordered-by user;
            key "pw-port-id";
            leaf pw-port-id {
              type string;
            }
            leaf vc-id {
              type string;
            }
            container egress {
              container shaping {
                choice choice {
                  leaf vport {
                    type string;
                  }
                  leaf int-dest-id {
                    type string;
                  }
                }
              }
            }
            leaf vc-type {
              type string;
            }
            leaf vlan-vc-tag {
              type string;
            }
            leaf shutdown {
              // NCS drop default statement
              type string;
            }
          }
        }
        leaf booking-factor {
          type string;
        }
        leaf collect-stats {
          type empty;
        }
        leaf delivery-type {
          type string;
        }
        leaf description {
          type string;
        }
        leaf far-end {
          type string;
        }
        container keep-alive {
          leaf hello-time {
            type string;
          }
          leaf hold-down-time {
            type string;
          }
          leaf max-drop-count {
            type string;
          }
          leaf message-length {
            type string;
          }
          leaf timeout {
            type string;
          }
          leaf shutdown {
            // NCS drop default statement
            type string;
          }
        }
        leaf ldp {
          type empty;
        }
        leaf lsp {
          // NCS drop tailf-common:cli-diff-dependency statement
          // NCS drop tailf-common:cli-diff-dependency statement
          type string;
        }
        container class-forwarding {
          leaf default-lsp {
            type string;
          }
          leaf enforce-diffserv-lsp-fc {
            type empty;
          }
          leaf fc {
            type string;
          }
          leaf multicast-lsp {
            type string;
          }
          leaf shutdown {
            // NCS drop default statement
            type string;
          }
        }
        leaf metric {
          type string;
        }
        container mixed-lsp-mode {
          leaf revert-time {
            type string;
          }
        }
        leaf network-domain {
          type string;
        }
        leaf path-mtu {
          type string;
        }
        leaf pbb-etype {
          type string;
        }
        leaf signaling {
          type string;
        }
        leaf local-end {
          type string;
        }
        leaf tunnel-far-end {
          type string;
        }
        leaf vlan-vc-etype {
          type string;
        }
        leaf shutdown {
          // NCS drop default statement
          type string;
        }
      }
      list epipe {
        // NCS patched for predictable order
        ordered-by user;
        // NCS drop tailf-common:cli-diff-dependency statement
        // NCS drop tailf-common:cli-diff-dependency statement
        key "service-id";
        leaf service-id {
          type string;
        }
        leaf customer {
          type string;
        }
        leaf description {
          type string;
        }
        leaf vc-switching {
          type empty;
        }
        list sap {
          // NCS patched for predictable order
          ordered-by user;
          // NCS drop tailf-common:cli-diff-dependency statement
          // NCS drop tailf-common:cli-diff-dependency statement
          key "sap-id";
          leaf sap-id {
            // NCS drop tailf-common:cli-diff-dependency statement
            // NCS drop tailf-common:cli-diff-dependency statement
            // NCS drop tailf-common:cli-diff-dependency statement
            // NCS drop tailf-common:cli-diff-dependency statement
            type string;
          }
          leaf endpoint {
            type string;
          }
          container egress {
            leaf qos {
              type string;
            }
          }
          container ingress {
            leaf qos {
              type string;
            }
          }
          leaf description {
            type string;
          }
          container eth-cfm {
            uses ncs_template_eth-cfm;
          }
          leaf multi-service-site {
            type string;
          }
          leaf oper-group {
            type string;
          }
          leaf shutdown {
            type empty;
          }
        }
        leaf service-name {
          type string;
        }
        leaf service-mtu {
          type string;
        }
        list site {
          // NCS patched for predictable order
          ordered-by user;
          key "name";
          leaf name {
            type string;
          }
          leaf boot-timer {
            type string;
          }
          leaf sap {
            type string;
          }
          leaf site-activation-timer {
            type string;
          }
          leaf site-id {
            type string;
          }
          leaf shutdown {
            // NCS drop default statement
            type string;
          }
        }
        list spoke-sdp {
          // NCS patched for predictable order
          ordered-by user;
          uses ncs_template_sdp-common;
          key "sdp-id vc-id";
          container egress {
            container l2tpv3 {
              leaf cookie {
                type string;
              }
            }
          }
          container ingress {
            container l2tpv3 {
              leaf cookie {
                type string;
              }
            }
          }
          leaf pw-status-signaling {
            type empty;
          }
          leaf control-word {
            type empty;
          }
          leaf precedence {
            type string;
          }
        }
        list endpoint {
          // NCS patched for predictable order
          ordered-by user;
          key "endpoint-name";
          leaf endpoint-name {
            type string;
          }
          leaf active-hold-delay {
            type string;
          }
          leaf description {
            type string;
          }
          leaf revert-time {
            type string;
          }
          leaf standby-signaling-master {
            type empty;
          }
          leaf standby-signaling-slave {
            type empty;
          }
        }
        leaf shutdown {
          // NCS drop default statement
          type string;
        }
      }
      list oper-group {
        // NCS patched for predictable order
        ordered-by user;
        key "group-name";
        leaf group-name {
          type string;
        }
        container hold-time {
          leaf group {
            type empty;
          }
        }
      }
      list ies {
        // NCS patched for predictable order
        ordered-by user;
        // NCS drop tailf-common:cli-diff-dependency statement
        // NCS drop tailf-common:cli-diff-dependency statement
        key "service-id";
        leaf service-id {
          type string;
        }
        leaf customer {
          type string;
        }
        leaf description {
          type string;
        }
        list subscriber-interface {
          // NCS patched for predictable order
          ordered-by user;
          key "id";
          leaf id {
            type string;
          }
          leaf address {
            type string;
          }
          list group-interface {
            // NCS patched for predictable order
            ordered-by user;
            key "id";
            leaf id {
              type string;
            }
            leaf description {
              type string;
            }
            container icmp {
              leaf mask-reply {
                type string;
              }
              container redirects {
                leaf number {
                  type string;
                }
                leaf seconds {
                  type string;
                }
              }
              container unreachables {
                leaf number {
                  type string;
                }
                leaf seconds {
                  type string;
                }
              }
              container ttl-expired {
                leaf number {
                  type string;
                }
                leaf seconds {
                  type string;
                }
              }
            }
            container ipv6 {
              container router-advertisements {
                leaf managed-configuration {
                  type empty;
                }
                leaf shutdown {
                  // NCS drop default statement
                  type string;
                }
              }
              container dhcp6 {
                container proxy-server {
                  container lease-time {
                    leaf days {
                      type string;
                    }
                    leaf hrs {
                      type string;
                    }
                    leaf min {
                      type string;
                    }
                    leaf sec {
                      type string;
                    }
                  }
                  leaf shutdown {
                    // NCS drop default statement
                    type string;
                  }
                }
              }
            }
            leaf arp-populate {
              type empty;
            }
            container dhcp {
              container proxy-server {
                container lease-time {
                  leaf days {
                    type string;
                  }
                  leaf hrs {
                    type string;
                  }
                  leaf min {
                    type string;
                  }
                  leaf sec {
                    type string;
                  }
                }
                leaf shutdown {
                  // NCS drop default statement
                  type string;
                }
              }
              container option {
                leaf action {
                  type string;
                }
                container circuit-id {
                  presence "true";
                  leaf id {
                    type string;
                  }
                }
                container remote-id {
                  presence "true";
                  choice remote-id {
                    leaf mac {
                      type string;
                    }
                    leaf string {
                      type string;
                    }
                  }
                }
              }
              leaf-list server {
                // NCS patched for predictable order
                ordered-by user;
                type string;
              }
              leaf trusted {
                type empty;
              }
              container lease-populate {
                presence "true";
                leaf nr-of-leases {
                  type string;
                }
                leaf l2-header {
                  type empty;
                }
                leaf mac {
                  type string;
                }
              }
              container gi-address {
                leaf address {
                  type string;
                }
                leaf src-ip-address {
                  type empty;
                }
              }
              leaf shutdown {
                // NCS drop default statement
                type string;
              }
            }
            list sap {
              // NCS patched for predictable order
              ordered-by user;
              key "id";
              leaf id {
                type string;
              }
              leaf description {
                type string;
              }
              leaf anti-spoof {
                type string;
              }
              container sub-sla-mgmt {
                container def-sub-id {
                  choice sub-id-choice {
                    leaf string {
                      type string;
                    }
                    leaf use-auto-id {
                      type empty;
                    }
                    leaf use-sap-id {
                      type empty;
                    }
                  }
                }
                leaf def-sub-profile {
                  type string;
                }
                leaf def-sla-profile {
                  type string;
                }
                container single-sub-parameters {
                  leaf profiled-traffic-only {
                    type empty;
                  }
                }
                leaf shutdown {
                  // NCS drop default statement
                  type string;
                }
              }
              leaf calling-station-id {
                type string;
              }
              leaf shutdown {
                // NCS drop default statement
                type string;
              }
            }
          }
        }
        list interface {
          // NCS patched for predictable order
          ordered-by user;
          // NCS drop tailf-common:cli-diff-dependency statement
          // NCS drop tailf-common:cli-diff-dependency statement
          key "ip-int-name";
          leaf ip-int-name {
            type string;
          }
          leaf address {
            type string;
          }
          leaf allow-directed-broadcasts {
            type empty;
          }
          leaf arp-populate {
            type empty;
          }
          leaf arp-timeout {
            type string;
          }
          leaf authentication-policy {
            type string;
          }
          container bfd {
            leaf transmit-interval {
              type string;
            }
            leaf receive {
              type string;
            }
            leaf multiplier {
              type string;
            }
            leaf echo-receive {
              type string;
            }
            leaf type {
              type string;
            }
          }
          container cflowd {
            leaf id {
              type string;
            }
            leaf direction {
              type string;
            }
          }
          leaf cpu-protection {
            type string;
          }
          leaf delayed-enable {
            type string;
          }
          leaf description {
            type string;
          }
          container dhcp;
          leaf dynamic-tunnel-redundant-next-hop {
            type string;
          }
          leaf enable-ingress-stats {
            type empty;
          }
          leaf enable-mac-accounting {
            type empty;
          }
          container host-connectivity {
            leaf source {
              type string;
            }
            leaf interval {
              type string;
            }
            leaf action {
              type string;
            }
            leaf timeout {
              type string;
            }
            leaf count {
              type string;
            }
          }
          container icmp {
            leaf mask-reply {
              type empty;
            }
            container redirects {
              leaf number {
                type string;
              }
              leaf seconds {
                type string;
              }
            }
            container ttl-expired {
              leaf number {
                type string;
              }
              leaf seconds {
                type string;
              }
            }
            container unreachables {
              leaf number {
                type string;
              }
              leaf seconds {
                type string;
              }
            }
          }
          leaf ip-mtu {
            type string;
          }
          container ipv6 {
            list address {
              // NCS patched for predictable order
              ordered-by user;
              key "addr";
              leaf addr {
                type string;
              }
            }
            container dhcp6-relay {
              leaf description {
                type string;
              }
              container lease-populate {
                presence "present";
                leaf nbr-of-leases {
                  type string;
                }
                leaf route-populate {
                  type empty;
                }
                leaf pd {
                  type empty;
                }
                leaf exclude {
                  type empty;
                }
                leaf na {
                  type empty;
                }
                leaf ta {
                  type empty;
                }
              }
              leaf neighbor-resolution {
                type empty;
              }
              container option {
                container interface-id {
                  choice choice {
                    leaf sap-id {
                      type empty;
                    }
                    leaf ifindex {
                      type empty;
                    }
                    leaf string {
                      type string;
                    }
                  }
                }
                leaf remote-id {
                  type empty;
                }
              }
              leaf source-address {
                type string;
              }
              leaf link-address {
                type string;
              }
              list server {
                // NCS patched for predictable order
                ordered-by user;
                // NCS drop max-elements statement
                key "ipv6z-address";
                leaf ipv6z-address {
                  type string;
                }
              }
              leaf shutdown {
                // NCS drop default statement
                type string;
              }
            }
            container urpf-check {
              leaf ignore-default {
                type empty;
              }
              container mode {
                choice choice {
                  leaf strict {
                    type empty;
                  }
                  leaf loose {
                    type empty;
                  }
                  leaf strict-no-ecmp {
                    type empty;
                  }
                }
              }
            }
          }
          list sap {
            // NCS patched for predictable order
            ordered-by user;
            // NCS drop max-elements statement
            key "sap-id";
            leaf sap-id {
              // NCS drop tailf-common:cli-diff-dependency statement
              // NCS drop tailf-common:cli-diff-dependency statement
              // NCS drop tailf-common:cli-diff-dependency statement
              // NCS drop tailf-common:cli-diff-dependency statement
              type string;
            }
            leaf description {
              type string;
            }
            container egress {
              container agg-rate-limit {
                leaf agg-rate {
                  type string;
                }
                leaf queue-frame-based-accounting {
                  type empty;
                }
              }
              container filter {
                leaf ip {
                  type string;
                }
                leaf ipv6 {
                  type string;
                }
              }
              leaf policer-control-policy {
                type string;
              }
              leaf qinq-mark-top-only {
                type empty;
              }
              leaf qos {
                type string;
              }
              container queue-override {
                uses ncs_template_queue-override-grouping;
              }
              leaf scheduler-policy {
                type string;
              }
            }
            container ingress {
              leaf qos {
                type string;
              }
              container filter {
                leaf ip {
                  type string;
                }
                leaf ipv6 {
                  type string;
                }
              }
              container queue-override {
                uses ncs_template_queue-override-grouping;
              }
            }
            leaf anti-spoof {
              type string;
            }
            leaf multi-service-site {
              type string;
            }
            container sub-sla-mgmt {
              presence "present";
              leaf def-sub-id {
                type string;
              }
              leaf def-sub-profile {
                type string;
              }
              container single-sub-parameters {
                presence "present";
                leaf profiled-traffic-only {
                  type empty;
                }
              }
              leaf shutdown {
                // NCS drop default statement
                type string;
              }
            }
            leaf calling-station-id {
              type string;
            }
            leaf shutdown {
              type empty;
            }
          }
          leaf tos-marking-state {
            type string;
            // NCS drop default statement
          }
          container urpf-check {
            leaf mode {
              type string;
            }
          }
          leaf shutdown {
            type empty;
          }
        }
        leaf shutdown {
          // NCS drop default statement
          type string;
        }
      }
      list vpls {
        // NCS patched for predictable order
        ordered-by user;
        // NCS drop tailf-common:cli-diff-dependency statement
        // NCS drop tailf-common:cli-diff-dependency statement
        key "service-id";
        leaf service-id {
          type ncs_template_vpls-id;
        }
        leaf customer {
          type string;
        }
        leaf vpn {
          type string;
        }
        leaf m-vpls {
          type empty;
        }
        choice a {
          leaf b-vpls {
            type empty;
          }
          leaf i-vpls {
            type empty;
          }
        }
        leaf description {
          type string;
        }
        leaf disable-learning {
          type empty;
        }
        leaf disable-aging {
          type empty;
        }
        leaf discard-unknown {
          type empty;
        }
        leaf allow-ip-int-binding {
          type empty;
        }
        leaf service-name {
          type string;
        }
        container eth-cfm {
          uses ncs_template_eth-cfm;
          leaf tunnel-fault {
            type string;
          }
        }
        leaf fdb-table-high-wmark {
          type string;
        }
        leaf fdb-table-low-wmark {
          type string;
        }
        leaf fdb-table-size {
          type string;
        }
        container igmp-snooping {
          leaf query-interval {
            type string;
          }
          leaf report-src-ip {
            type string;
          }
          leaf robust-count {
            type string;
          }
          leaf shutdown {
            // NCS drop default statement
            type string;
          }
        }
        list interface {
          // NCS patched for predictable order
          ordered-by user;
          key "ip-int-name";
          leaf ip-int-name {
            type string;
          }
          container address {
            choice a {
              leaf addr-and-prefix {
                type string;
              }
              case addr-and-netmask {
                leaf addr {
                  type string;
                }
                leaf mask {
                  type string;
                }
              }
            }
          }
          leaf arp-timeout {
            type string;
          }
          leaf description {
            type string;
          }
          leaf mac {
            type ncs_template_ieee-mac;
          }
          list static-arp {
            // NCS patched for predictable order
            ordered-by user;
            key "address";
            leaf address {
              type string;
            }
            leaf ieee-address {
              type ncs_template_ieee-mac;
            }
            leaf unnumbered {
              type empty;
            }
          }
          leaf unnumbered {
            type string;
          }
          leaf shutdown {
            // NCS drop default statement
            type string;
          }
        }
        leaf local-age {
          type string;
        }
        container mac-move {
          leaf move-frequency {
            type string;
          }
          leaf retry-timeout {
            type string;
          }
          leaf shutdown {
            // NCS drop default statement
            type string;
          }
        }
        leaf mfib-table-high-wmark {
          type string;
        }
        leaf mfib-table-low-wmark {
          type string;
        }
        leaf mfib-table-size {
          type string;
        }
        leaf remote-age {
          type string;
        }
        leaf send-flush-on-failure {
          type empty;
        }
        leaf service-mtu {
          type string;
        }
        list spb {
          // NCS patched for predictable order
          ordered-by user;
          key "isis-instance";
          leaf isis-instance {
            type string;
          }
          leaf fid {
            type string;
          }
          list level {
            // NCS patched for predictable order
            ordered-by user;
            key "level";
            leaf level {
              type string;
            }
            leaf bridge-priority {
              type string;
            }
            container ect-algorithm {
              leaf fid-range {
                type string;
              }
              leaf path-id {
                type string;
              }
            }
            container forwarding-tree-topology {
              leaf unicast {
                type string;
              }
            }
            leaf hello-interval {
              type string;
            }
            leaf hello-multiplier {
              type string;
            }
            leaf metric {
              type string;
            }
          }
          leaf lsp-pacing-interval {
            type string;
          }
          leaf retransmit-interval {
            type string;
          }
          leaf shutdown {
            // NCS drop default statement
            type string;
          }
        }
        container stp {
          leaf forward-delay {
            type string;
          }
          leaf hello-time {
            type string;
          }
          leaf hold-count {
            type string;
          }
          leaf max-age {
            type string;
          }
          leaf mode {
            type string;
          }
          list mst-instance {
            // NCS patched for predictable order
            ordered-by user;
            key "mst-inst-number";
            leaf mst-inst-number {
              type string;
            }
            leaf mst-priority {
              type string;
            }
            leaf vlan-range {
              type string;
            }
          }
          leaf mst-max-hops {
            type string;
          }
          leaf mst-name {
            type string;
          }
          leaf mst-revision {
            type string;
          }
          leaf priority {
            type string;
          }
          leaf shutdown {
            // NCS drop default statement
            type string;
          }
        }
        leaf def-mesh-vc-id {
          type string;
        }
        list mesh-sdp {
          // NCS patched for predictable order
          ordered-by user;
          uses ncs_template_sdp-spoke-mesh-common;
          key "sdp-id vc-id";
        }
        container pim-snooping {
          leaf shutdown {
            // NCS drop default statement
            type string;
          }
        }
        list spoke-sdp {
          // NCS patched for predictable order
          ordered-by user;
          uses ncs_template_sdp-spoke-mesh-common;
          key "sdp-id vc-id";
          leaf split-horizon-group {
            type string;
          }
          leaf force-vlan-vc-forwarding {
            type empty;
          }
          leaf bpdu-translation {
            type string;
          }
          leaf diable-aging {
            type empty;
          }
          leaf disable-learning {
            type empty;
          }
          leaf discard-unknown-source {
            type empty;
          }
          leaf l2pt-termination {
            type empty;
          }
          leaf limit-mac-move {
            type ncs_template_limit-mac-move;
          }
          leaf max-nbr-mac-addr {
            type string;
          }
          container stp {
            uses ncs_template_stp-common;
          }
          container transit-policy {
            leaf prefix {
              type string;
            }
          }
        }
        list sap {
          // NCS patched for predictable order
          ordered-by user;
          key "sap-id";
          leaf sap-id {
            // NCS drop tailf-common:cli-diff-dependency statement
            // NCS drop tailf-common:cli-diff-dependency statement
            // NCS drop tailf-common:cli-diff-dependency statement
            // NCS drop tailf-common:cli-diff-dependency statement
            type string;
          }
          leaf split-horizon-group {
            type string;
          }
          leaf accounting-policy {
            type string;
          }
          leaf anti-spoof {
            type string;
          }
          leaf app-profile {
            type string;
          }
          leaf auto-learn-mac-protect {
            type empty;
          }
          leaf bpdu-translation {
            type string;
          }
          leaf collect-stats {
            type empty;
          }
          leaf description {
            type string;
          }
          leaf disable-aging {
            type empty;
          }
          leaf disable-learning {
            type empty;
          }
          leaf discard-unknown-source {
            type empty;
          }
          container eth-cfm {
            uses ncs_template_eth-cfm;
            leaf mip {
              type empty;
            }
          }
          container igmp-snooping {
            uses ncs_template_igmp-snooping;
          }
          container ingress {
            uses ncs_template_sap-ingress-grouping;
          }
          leaf lag-link-map-profile {
            type string;
          }
          leaf l2pt-termination {
            type empty;
          }
          leaf limit-mac-move {
            type ncs_template_limit-mac-move;
          }
          leaf mac-pinning {
            type empty;
          }
          container managed-vlan-list {
            leaf default-sap {
              type empty;
            }
            leaf range {
              type string;
            }
          }
          leaf max-nbr-mac-addr {
            type string;
          }
          leaf monitor-oper-group {
            type string;
          }
          leaf multi-service-site {
            type string;
            // NCS drop tailf-common:cli-diff-dependency statement
          }
          container restrict-protected-src {
            presence "present";
            leaf restrict-protected-src-value {
              type string;
            }
          }
          leaf restrict-unprotected-dst {
            type empty;
          }
          leaf ring-node {
            type empty;
          }
          leaf static-mac {
            type ncs_template_ieee-mac;
          }
          container egress {
            uses ncs_template_sap-egress-grouping;
          }
          container stp {
            uses ncs_template_stp-common;
            list mst-instance {
              // NCS patched for predictable order
              ordered-by user;
              // NCS drop max-elements statement
              key "mst-inst-number";
              leaf mst-inst-number {
                type string;
              }
              leaf mst-path-cost {
                type string;
              }
              leaf mst-priority {
                type string;
              }
            }
          }
          leaf tod-suite {
            type string;
          }
          leaf shutdown {
            type empty;
          }
        }
        list split-horizon-group {
          // NCS patched for predictable order
          ordered-by user;
          key "group-name";
          leaf group-name {
            type string;
          }
          leaf residential-group {
            type empty;
          }
          leaf auto-learn-mac-protect {
            type empty;
          }
          leaf description {
            type string;
          }
          leaf restrict-protected-src {
            type empty;
          }
          leaf restrict-unprotected-src {
            type empty;
          }
        }
        container bgp {
          list pw-template-binding {
            // NCS patched for predictable order
            ordered-by user;
            key "policy-id";
            leaf policy-id {
              type string;
            }
          }
        }
        container bgp-ad {
          presence "true";
          leaf vpls-id {
            type ncs_template_vpls-id;
          }
          leaf shutdown {
            // NCS drop default statement
            type string;
          }
        }
        container bgp-vpls {
          leaf max-ve-id {
            type string;
          }
          container ve-name {
            leaf ve-name-value {
              type string;
            }
            leaf ve-id {
              type string;
            }
          }
          leaf shutdown {
            type empty;
          }
        }
        leaf shutdown {
          // NCS drop default statement
          type string;
        }
      }
      list vprn {
        // NCS patched for predictable order
        ordered-by user;
        // NCS drop tailf-common:cli-diff-dependency statement
        // NCS drop tailf-common:cli-diff-dependency statement
        key "service-id";
        leaf service-id {
          type ncs_template_vpls-id;
        }
        leaf customer {
          type string;
        }
        leaf auto-bind {
          type string;
        }
        container bgp {
          leaf damping {
            type empty;
          }
          leaf router-id {
            type string;
          }
          list group {
            // NCS patched for predictable order
            ordered-by user;
            key "name";
            leaf name {
              type string;
            }
            leaf as-override {
              type empty;
            }
            container authentication-key {
              leaf key {
                type string;
              }
              leaf type {
                type string;
              }
            }
            leaf bfd-enable {
              type empty;
            }
            leaf description {
              type string;
            }
            leaf-list export {
              // NCS patched for predictable order
              ordered-by user;
              // NCS drop max-elements statement
              type string;
            }
            leaf-list import {
              // NCS patched for predictable order
              ordered-by user;
              // NCS drop max-elements statement
              type string;
            }
            leaf local-address {
              type string;
            }
            list neighbor {
              // NCS patched for predictable order
              ordered-by user;
              key "address";
              leaf address {
                type string;
              }
              leaf advertise-inactive {
                type empty;
              }
              leaf description {
                type string;
              }
              leaf-list family {
                // NCS patched for predictable order
                ordered-by user;
                type string;
              }
              leaf local-address {
                type string;
              }
              leaf med-out {
                type string;
              }
              leaf multihop {
                type string;
              }
              leaf peer-as {
                type string;
              }
              container remove-private {
                presence "true";
                leaf-list options {
                  // NCS patched for predictable order
                  ordered-by user;
                  type string;
                }
              }
              leaf split-horizon {
                type empty;
              }
              leaf type {
                type string;
              }
            }
            container prefix-limit {
              leaf limit {
                type string;
              }
              leaf log-only {
                type empty;
              }
              leaf treshold {
                type string;
              }
              leaf idle-timeout {
                type string;
              }
            }
            leaf peer-as {
              type string;
            }
            container remove-private {
              presence "true";
              leaf-list options {
                // NCS patched for predictable order
                ordered-by user;
                type string;
              }
            }
            leaf type {
              type string;
            }
            leaf shutdown {
              // NCS drop default statement
              type string;
            }
          }
          leaf med-out {
            type string;
          }
          leaf min-route-advertisement {
            type string;
          }
          leaf shutdown {
            // NCS drop default statement
            type string;
          }
        }
        leaf description {
          type string;
        }
        container dhcp {
          list local-dhcp-server {
            // NCS patched for predictable order
            ordered-by user;
            key "server-name";
            leaf server-name {
              type string;
            }
            leaf description {
              type string;
            }
            leaf force-renews {
              type empty;
            }
            list pool {
              // NCS patched for predictable order
              ordered-by user;
              key "pool-id";
              leaf pool-id {
                type string;
              }
              leaf description {
                type string;
              }
              container max-lease-time {
                uses ncs_template_dhcp-lease-time;
              }
              container min-lease-time {
                uses ncs_template_dhcp-lease-time;
              }
              container minimum-free {
                leaf minimum-free-value {
                  type string;
                }
                leaf percent {
                  type empty;
                }
                leaf event-when-depleted {
                  type empty;
                }
              }
              leaf nak-non-matching-subnet {
                type empty;
              }
              container offer-time {
                leaf min {
                  type string;
                }
                leaf sec {
                  type string;
                }
              }
              container options {
                leaf-list dns-server {
                  // NCS patched for predictable order
                  ordered-by user;
                  type string;
                }
                leaf domain-name {
                  type string;
                }
                container lease-rebind-time {
                  uses ncs_template_dhcp-lease-time;
                }
                container lease-renew-time {
                  uses ncs_template_dhcp-lease-time;
                }
                container lease-time {
                  uses ncs_template_dhcp-lease-time;
                }
                leaf-list netbios-name-server {
                  // NCS patched for predictable order
                  ordered-by user;
                  type string;
                }
                leaf netbios-node-type {
                  type string;
                }
              }
              list subnet {
                // NCS patched for predictable order
                ordered-by user;
                key "subnet-id";
                leaf subnet-id {
                  type string;
                }
                container address-range {
                  uses ncs_template_ip-address-range;
                }
                leaf drain {
                  type empty;
                }
                container exclude-addresses {
                  uses ncs_template_ip-address-range;
                }
                leaf maximum-declined {
                  type string;
                }
                container minimum-free {
                  leaf minimum-free-value {
                    type string;
                  }
                  leaf percent {
                    type empty;
                  }
                  leaf event-when-depleted {
                    type empty;
                  }
                }
                container options {
                  leaf-list default-router {
                    // NCS patched for predictable order
                    ordered-by user;
                    type string;
                  }
                  leaf subnet-mask {
                    type string;
                  }
                }
              }
            }
            leaf shutdown {
              type string;
            }
          }
        }
        list interface {
          // NCS patched for predictable order
          ordered-by user;
          key "ip-int-name";
          leaf ip-int-name {
            type string;
          }
          leaf tunnel {
            type empty;
          }
          leaf address {
            type string;
          }
          container bfd {
            leaf id {
              type string;
            }
            leaf receive {
              type string;
            }
            leaf multiplier {
              type string;
            }
            leaf type {
              type string;
            }
          }
          container dhcp {
            leaf description {
              type string;
            }
            container gi-address {
              leaf gi-address-value {
                type string;
              }
              leaf src-ip-addr {
                type empty;
              }
            }
            leaf lease-populate {
              type string;
            }
            leaf-list server {
              // NCS patched for predictable order
              ordered-by user;
              type string;
            }
            leaf trusted {
              type empty;
            }
            leaf use-arp {
              type empty;
            }
            leaf shutdown {
              // NCS drop default statement
              type string;
            }
          }
          leaf secondary {
            type string;
          }
          leaf description {
            type string;
          }
          leaf ip-mtu {
            type string;
          }
          leaf loopback {
            type empty;
          }
          list sap {
            // NCS patched for predictable order
            ordered-by user;
            key "sap-id";
            leaf sap-id {
              // NCS drop tailf-common:cli-diff-dependency statement
              // NCS drop tailf-common:cli-diff-dependency statement
              // NCS drop tailf-common:cli-diff-dependency statement
              // NCS drop tailf-common:cli-diff-dependency statement
              type string;
            }
            leaf accounting-policy {
              type string;
            }
            leaf anti-spoof {
              type string;
            }
            leaf collect-stats {
              type empty;
            }
            leaf description {
              type string;
            }
            leaf multi-service-site {
              type string;
            }
            container egress {
              uses ncs_template_sap-egress-grouping;
            }
            container eth-cfm {
              uses ncs_template_eth-cfm;
            }
            container ingress {
              uses ncs_template_sap-ingress-grouping;
            }
            container ipsectunnel {
              uses ncs_template_sap-ingress-grouping;
            }
            leaf lag-link-map-profile {
              type string;
            }
            leaf shutdown {
              // NCS drop default statement
              type string;
            }
          }
          list spoke-sdp {
            // NCS patched for predictable order
            ordered-by user;
            uses ncs_template_sdp-common;
            key "sdp-id vc-id";
          }
          container urpf-check {
            leaf mode {
              type string;
            }
          }
          list vpls {
            // NCS patched for predictable order
            ordered-by user;
            key "service-name";
            leaf service-name {
              type string;
            }
            container egress {
              leaf reclassify-using-qos {
                type string;
              }
            }
          }
          container ipv6 {
            leaf address {
              type string;
            }
          }
          leaf shutdown {
            // NCS drop default statement
            type string;
          }
        }
        container ipsec {
          list security-policy {
            // NCS patched for predictable order
            ordered-by user;
            key "security-policy-id";
            leaf security-policy-id {
              type string;
            }
            list entry {
              // NCS patched for predictable order
              ordered-by user;
              key "entry-id";
              leaf entry-id {
                type string;
              }
              leaf local-ip {
                type string;
              }
              leaf local-v6-ip {
                type string;
              }
              leaf remote-ip {
                type string;
              }
              leaf remote-v6-ip {
                type string;
              }
            }
          }
        }
        container maximum-routes {
          leaf routes {
            type string;
          }
          leaf log-only {
            type empty;
          }
          leaf threshold {
            type string;
          }
        }
        leaf route-distinguisher {
          type string;
        }
        leaf-list vrf-export {
          // NCS patched for predictable order
          ordered-by user;
          // NCS drop max-elements statement
          type string;
        }
        leaf-list vrf-import {
          // NCS patched for predictable order
          ordered-by user;
          // NCS drop max-elements statement
          type string;
        }
        container vrf-target {
          choice vrf {
            leaf ext-community {
              type empty;
            }
            leaf export {
              type string;
            }
            leaf import {
              type string;
            }
            leaf ext-community-value {
              type string;
            }
          }
        }
        leaf autonomous-system {
          type string;
        }
        list spoke-sdp {
          // NCS patched for predictable order
          ordered-by user;
          key "sdp-id";
          leaf sdp-id {
            type string;
          }
          leaf description {
            type string;
          }
        }
        list static-route {
          // NCS patched for predictable order
          ordered-by user;
          key "route";
          leaf route {
            type string;
          }
          choice nh {
            leaf next-hop {
              type string;
            }
            leaf indirect {
              type string;
            }
            leaf ipsec-tunnel {
              type string;
            }
            leaf black-hole {
              type empty;
            }
          }
          leaf preference {
            type string;
          }
          leaf metric {
            type string;
          }
          choice ed {
            leaf enable {
              type empty;
            }
            leaf disable {
              type empty;
            }
          }
          leaf tag {
            type string;
          }
          leaf bfd-enable {
            type empty;
          }
          leaf log {
            type empty;
          }
          leaf prefix-list-name {
            type string;
          }
          choice an {
            leaf all {
              type empty;
            }
            leaf none {
              type empty;
            }
          }
        }
        container sgt-qos {
          list application {
            // NCS patched for predictable order
            ordered-by user;
            key "app-name";
            leaf app-name {
              type string;
            }
            leaf dscp {
              type string;
            }
          }
        }
        container pim {
          list interface {
            // NCS patched for predictable order
            ordered-by user;
            key "name";
            leaf name {
              type string;
            }
          }
          container rp {
            container static {
              presence "true";
              list address {
                // NCS patched for predictable order
                ordered-by user;
                key "address";
                leaf address {
                  type string;
                }
                list group-prefix {
                  // NCS patched for predictable order
                  ordered-by user;
                  key "address";
                  leaf address {
                    type string;
                  }
                }
                leaf override {
                  type empty;
                }
              }
            }
            container bsr-candidate {
              leaf shutdown {
                // NCS drop default statement
                type string;
              }
            }
            container rp-candidate {
              leaf shutdown {
                // NCS drop default statement
                type string;
              }
            }
          }
        }
        container mvpn {
          leaf auto-discovery {
            type string;
          }
          leaf c-mcast-signaling {
            type string;
          }
          container provider-tunnel {
            container inclusive {
              container pim {
                presence "present";
                leaf multicast-type {
                  type string;
                }
                leaf grp-ip-address {
                  type string;
                }
                leaf shutdown {
                  // NCS drop default statement
                  type string;
                }
              }
              container rsvp {
                leaf lsp-template {
                  type string;
                }
                leaf shutdown {
                  // NCS drop default statement
                  type string;
                }
              }
            }
          }
          list vrf-target {
            // NCS patched for predictable order
            ordered-by user;
            key "id";
            leaf id {
              type string;
            }
            leaf export {
              type string;
            }
            leaf import {
              type string;
            }
          }
        }
        leaf router-id {
          type string;
        }
        list isis {
          // NCS patched for predictable order
          ordered-by user;
          key "id";
          leaf id {
            type string;
          }
          leaf area-id {
            type string;
          }
          leaf ipv6-routing {
            type string;
          }
          container multi-topology {
            leaf ipv6-unicast {
              type empty;
            }
          }
          list interface {
            // NCS patched for predictable order
            ordered-by user;
            key "name";
            leaf name {
              type string;
            }
            leaf passive {
              type empty;
            }
            leaf interface-type {
              type string;
            }
            leaf shutdown {
              // NCS drop default statement
              type string;
            }
          }
          leaf router-id {
            type string;
          }
          leaf shutdown {
            // NCS drop default statement
            type string;
          }
        }
        leaf shutdown {
          // NCS drop default statement
          type string;
        }
      }
      list pw-template {
        // NCS patched for predictable order
        ordered-by user;
        key "policy-id";
        leaf policy-id {
          type string;
        }
        leaf use-provisioned-sdp {
          type empty;
        }
        leaf force-vlan-vc-forwarding {
          type empty;
        }
        list split-horizon-group {
          // NCS patched for predictable order
          ordered-by user;
          key "group-name";
          leaf group-name {
            type string;
          }
          leaf auto-learn-mac-protect {
            type empty;
          }
          leaf description {
            type string;
          }
          container restrict-protected-src {
            presence "true";
            leaf option {
              type string;
            }
          }
          leaf restrict-unprotected-dst {
            type empty;
          }
        }
        leaf vc-type {
          // NCS drop default statement
          type string;
        }
      }
    }
    list router {
      // NCS patched for predictable order
      ordered-by user;
      key "router-name";
      leaf router-name {
        type string;
      }
      leaf autonomous-system {
        type string;
      }
      container bgp {
        presence "present";
        container add-paths {
          container ipv4 {
            leaf send {
              type string;
            }
            leaf receive {
              type string;
            }
          }
          container ipv6 {
            leaf send {
              type string;
            }
            leaf receive {
              type string;
            }
          }
          container vpn-ipv4 {
            leaf send {
              type string;
            }
            leaf receive {
              type string;
            }
          }
          container vpn-ipv6 {
            leaf send {
              type string;
            }
            leaf receive {
              type string;
            }
          }
        }
        leaf-list advertise-external {
          // NCS patched for predictable order
          ordered-by user;
          type string;
        }
        leaf advertise-inactive {
          type empty;
        }
        leaf aggregator-id-zero {
          type empty;
        }
        leaf auth-keychain {
          type string;
        }
        container authentication-key {
          leaf key {
            type string;
          }
          leaf type {
            type string;
          }
        }
        leaf-list backup-path {
          // NCS patched for predictable order
          ordered-by user;
          type string;
        }
        container best-path-selection {
          container always-compare-med {
            leaf strict-as {
              type empty;
            }
            leaf type {
              type string;
            }
          }
          leaf-list as-path-ignore {
            // NCS patched for predictable order
            ordered-by user;
            type string;
          }
          leaf deterministic-med {
            type empty;
          }
          leaf ignore-nh-metric {
            type empty;
          }
          leaf ignore-router-id {
            type empty;
          }
        }
        leaf bfd-enable {
          type empty;
        }
        leaf cluster {
          type string;
        }
        leaf connect-retry {
          type string;
        }
        leaf damping {
          type empty;
        }
        leaf description {
          type string;
        }
        leaf disable-4byte-asn {
          type empty;
        }
        leaf disable-client-reflect {
          type empty;
        }
        leaf-list disable-communities {
          // NCS patched for predictable order
          ordered-by user;
          type string;
        }
        leaf disable-fast-external-failover {
          type empty;
        }
        leaf disable-route-table-install {
          type empty;
        }
        leaf enable-inter-as-vpn {
          type empty;
        }
        leaf enable-peer-tracking {
          type empty;
        }
        leaf enable-rr-vpn-forwarding {
          type empty;
        }
        leaf-list export {
          // NCS patched for predictable order
          ordered-by user;
          type string;
        }
        leaf-list family {
          // NCS patched for predictable order
          ordered-by user;
          type string;
        }
        leaf flowspec-validate {
          type empty;
        }
        container graceful-restart {
          leaf stale-routes-time {
            type string;
          }
        }
        list group {
          // NCS patched for predictable order
          ordered-by user;
          key "id";
          leaf id {
            type string;
          }
          container add-paths {
            container ipv4 {
              leaf send {
                type string;
              }
              leaf receive {
                type string;
              }
            }
            container ipv6 {
              leaf send {
                type string;
              }
              leaf receive {
                type string;
              }
            }
            container vpn-ipv4 {
              leaf send {
                type string;
              }
              leaf receive {
                type string;
              }
            }
            container vpn-ipv6 {
              leaf send {
                type string;
              }
              leaf receive {
                type string;
              }
            }
          }
          leaf advertise-inactive {
            type empty;
          }
          leaf aggregator-id-zero {
            type empty;
          }
          leaf aigp {
            type empty;
          }
          leaf auth-keychain {
            type string;
          }
          container authentication-key {
            leaf key {
              type string;
            }
            leaf type {
              type string;
            }
          }
          leaf bfd-enable {
            type empty;
          }
          leaf cluster {
            type string;
          }
          leaf connect-retry {
            type string;
          }
          leaf damping {
            type empty;
          }
          leaf default-route-target {
            type empty;
          }
          leaf description {
            type string;
          }
          leaf disable-4byte-asn {
            type empty;
          }
          leaf disable-capability-negotiation {
            type empty;
          }
          leaf disable-client-reflect {
            type empty;
          }
          leaf-list disable-communities {
            // NCS patched for predictable order
            ordered-by user;
            type string;
          }
          leaf disable-fast-external-failover {
            type empty;
          }
          leaf enable-peer-tracking {
            type empty;
          }
          leaf-list export {
            // NCS patched for predictable order
            ordered-by user;
            type string;
          }
          leaf-list family {
            // NCS patched for predictable order
            ordered-by user;
            type string;
          }
          leaf flowspec-validate {
            type empty;
          }
          container graceful-restart {
            leaf stale-routes-time {
              type string;
            }
          }
          container hold-time {
            leaf seconds {
              type string;
            }
            leaf min {
              type string;
            }
          }
          leaf-list import {
            // NCS patched for predictable order
            ordered-by user;
            type string;
          }
          leaf keepalive {
            type string;
          }
          leaf local-address {
            type string;
          }
          container local-as {
            leaf number {
              type string;
            }
            leaf private {
              type empty;
            }
            leaf no-prepend-global-as {
              type empty;
            }
          }
          leaf local-preference {
            type string;
          }
          leaf loop-detect {
            type string;
          }
          leaf med-out {
            type string;
          }
          leaf min-as-origination {
            type string;
          }
          leaf min-route-advertisement {
            type string;
          }
          leaf multihop {
            type string;
          }
          list neighbor {
            // NCS patched for predictable order
            ordered-by user;
            key "address";
            leaf address {
              type string;
            }
            leaf description {
              type string;
            }
            container authentication-key {
              leaf key {
                type string;
              }
              leaf hash {
                type string;
              }
            }
            leaf peer-as {
              type string;
            }
            container remove-private {
              presence "true";
              leaf-list options {
                // NCS patched for predictable order
                ordered-by user;
                type string;
              }
            }
            leaf shutdown {
              // NCS drop default statement
              type string;
            }
          }
          leaf next-hop-self {
            type empty;
          }
          container outbound-route-filtering {
            container extended-community {
              leaf accept-orf {
                type empty;
              }
              leaf-list send-orf {
                // NCS patched for predictable order
                ordered-by user;
                type string;
              }
            }
          }
          leaf passive {
            type empty;
          }
          leaf path-mtu-discovery {
            type empty;
          }
          leaf peer-as {
            type string;
          }
          leaf preference {
            type string;
          }
          container prefix-limit {
            leaf limit {
              type string;
            }
            leaf log-only {
              type empty;
            }
            leaf treshold {
              type string;
            }
            leaf idle-timeout {
              type string;
            }
          }
          container remove-private {
            presence "true";
            leaf-list options {
              // NCS patched for predictable order
              ordered-by user;
              type string;
            }
          }
          leaf split-horizon {
            type empty;
          }
          leaf ttl-security {
            type string;
          }
          leaf type {
            type string;
          }
          leaf vpn-apply-export {
            type empty;
          }
          leaf vpn-apply-import {
            type empty;
          }
          leaf shutdown {
            // NCS drop default statement
            type string;
          }
        }
        container hold-time {
          leaf seconds {
            type string;
          }
          leaf min {
            type string;
          }
        }
        leaf ibgp-multipath {
          type empty;
        }
        container igp-shortcut {
          leaf value {
            type string;
          }
          leaf disallow-igp {
            type empty;
          }
        }
        leaf-list import {
          // NCS patched for predictable order
          ordered-by user;
          type string;
        }
        leaf keepalive {
          type string;
        }
        container local-as {
          leaf number {
            type string;
          }
          leaf private {
            type empty;
          }
          leaf no-prepend-global-as {
            type empty;
          }
        }
        leaf local-preference {
          type string;
        }
        leaf loop-detect {
          type string;
        }
        leaf med-out {
          type string;
        }
        leaf min-as-origination {
          type string;
        }
        leaf min-route-advertisement {
          type string;
        }
        leaf mp-bgp-keep {
          type empty;
        }
        leaf multihop {
          type string;
        }
        leaf multipath {
          type string;
        }
        leaf mvpn-vrf-import-subtype-new {
          type empty;
        }
        container next-hop-resolution {
          leaf policy {
            type string;
          }
          leaf use-bgp-routes {
            type empty;
          }
        }
        container outbound-route-filtering {
          container extended-community {
            leaf accept-orf {
              type empty;
            }
            leaf-list send-orf {
              // NCS patched for predictable order
              ordered-by user;
              type string;
            }
          }
        }
        leaf path-mtu-discovery {
          type empty;
        }
        leaf peer-tracking-policy {
          type string;
        }
        leaf preference {
          type string;
        }
        leaf purge-timer {
          type string;
        }
        leaf-list rapid-update {
          // NCS patched for predictable order
          ordered-by user;
          type string;
        }
        leaf rapid-withdrawal {
          type empty;
        }
        leaf remove-private {
          type string;
        }
        leaf-list route-target-list {
          // NCS patched for predictable order
          ordered-by user;
          type string;
        }
        leaf router-id {
          type string;
        }
        leaf split-horizon {
          type empty;
        }
        leaf transport-tunnel {
          type string;
        }
        leaf vpn-apply-export {
          type empty;
        }
        leaf vpn-apply-import {
          type empty;
        }
        leaf shutdown {
          // NCS drop default statement
          type string;
        }
      }
      leaf ecmp {
        type string;
      }
      leaf fib-priority {
        type string;
      }
      leaf ldp-shortcut {
        // NCS drop default statement
        type string;
      }
      leaf router-id {
        type string;
      }
      list static-route {
        // NCS patched for predictable order
        ordered-by user;
        key "route";
        leaf route {
          type string;
        }
        choice nh {
          leaf next-hop {
            type string;
          }
          leaf indirect {
            type string;
          }
          leaf black-hole {
            type empty;
          }
        }
        leaf preference {
          type string;
        }
        leaf metric {
          type string;
        }
        choice ed {
          leaf enable {
            type empty;
          }
          leaf disable {
            type empty;
          }
        }
        leaf ldp {
          type empty;
        }
        leaf disallow-igp {
          type empty;
        }
        leaf tag {
          type string;
        }
        leaf bfd-enable {
          type empty;
        }
        leaf mcast-family {
          type string;
        }
        leaf rsvp-te {
          type empty;
        }
        leaf cpe-ip-address {
          type string;
        }
        leaf seconds {
          type string;
        }
        leaf count {
          type string;
        }
        leaf log {
          type empty;
        }
        leaf prefix-list-name {
          type string;
        }
        choice an {
          leaf all {
            type empty;
          }
          leaf none {
            type empty;
          }
        }
        leaf ldp-sync {
          type empty;
        }
        leaf fc-name {
          type string;
        }
        choice lh {
          leaf low {
            type empty;
          }
          leaf high {
            type empty;
          }
        }
      }
      list isis {
        // NCS patched for predictable order
        ordered-by user;
        key "id";
        leaf id {
          type string;
        }
        leaf all-l1isis {
          type string;
        }
        leaf all-l2isis {
          type string;
        }
        leaf area-id {
          type string;
        }
        leaf iid-tlv-enable {
          type empty;
        }
        leaf ipv4-routing {
          type empty;
        }
        leaf ipv4-multicast-routing {
          type string;
        }
        leaf ipv6-routing {
          type string;
        }
        leaf ipv6-multicast-routing {
          type string;
        }
        leaf lsp-lifetime {
          type string;
        }
        leaf lsp-refresh-interval {
          type string;
        }
        container lsp-wait {
          leaf wait {
            type string;
          }
          leaf initial-wait {
            type string;
          }
          leaf second-wait {
            type string;
          }
        }
        list level {
          // NCS patched for predictable order
          ordered-by user;
          key "id";
          leaf id {
            type string;
          }
          container authentication-key {
            leaf key {
              type string;
            }
            leaf keyword {
              type string;
            }
          }
          leaf authentication-type {
            type string;
          }
          leaf csnp-authentication {
            type empty;
          }
          leaf default-ipv6-unicast-metric {
            type string;
          }
          leaf default-metric {
            type string;
          }
          leaf external-preference {
            type string;
          }
          leaf hello-authentication {
            type empty;
          }
          leaf loopfree-alternate-exclude {
            type empty;
          }
          leaf preference {
            type string;
          }
          leaf psnp-authentication {
            type empty;
          }
          leaf wide-metrics-only {
            type empty;
          }
        }
        list link-group {
          // NCS patched for predictable order
          ordered-by user;
          key "name";
          leaf name {
            type string;
          }
          list level {
            // NCS patched for predictable order
            ordered-by user;
            key "id";
            leaf id {
              type string;
            }
            leaf ipv6-unicast-metric-offset {
              type string;
            }
            list member {
              // NCS patched for predictable order
              ordered-by user;
              key "name";
              leaf name {
                type string;
              }
            }
            leaf revert-members {
              type string;
            }
            leaf oper-members {
              type string;
            }
          }
        }
        container multi-topology {
          leaf ipv6-unicast {
            type empty;
          }
        }
        list interface {
          // NCS patched for predictable order
          ordered-by user;
          key "name";
          leaf name {
            type string;
          }
          leaf bfd-enable {
            type string;
          }
          leaf csnp-interval {
            type string;
          }
          leaf hello-authentication {
            type empty;
          }
          container hello-authentication-key {
            leaf key {
              type string;
            }
            leaf type {
              type string;
            }
          }
          leaf hello-authentication-type {
            type string;
          }
          leaf interface-type {
            type string;
          }
          leaf ipv4-multicast-enable {
            type empty;
          }
          leaf ipv6-multicast-enable {
            type empty;
          }
          leaf ipv6-unicast-enable {
            type empty;
          }
          list level {
            // NCS patched for predictable order
            ordered-by user;
            key "id";
            leaf id {
              type string;
            }
            container hello-authentication-key {
              leaf key {
                type string;
              }
              leaf type {
                type string;
              }
            }
            leaf hello-authentication-type {
              type string;
            }
            leaf hello-interval {
              type string;
            }
            leaf hello-multiplier {
              type string;
            }
            leaf ipv4-multicast-metric {
              type string;
            }
            leaf ipv6-multicast-metric {
              type string;
            }
            leaf ipv6-unicast-metric {
              type string;
            }
            leaf metric {
              type string;
            }
            leaf passive {
              type empty;
            }
            leaf priority {
              type string;
            }
            leaf sd-offset {
              type string;
            }
            leaf sf-offset {
              type string;
            }
          }
          leaf level-capability {
            type string;
          }
          leaf loopfree-alternate-exclude {
            type empty;
          }
          leaf lsp-pacing-interval {
            type string;
          }
          leaf mesh-group {
            type string;
          }
          leaf passive {
            type empty;
          }
          leaf retransmit-interval {
            type string;
          }
          leaf tag {
            type string;
          }
          leaf shutdown {
            // NCS drop default statement
            type string;
          }
        }
        leaf level-capability {
          type string;
        }
        container spf-wait {
          leaf wait {
            type string;
          }
          leaf initial-wait {
            type string;
          }
          leaf second-wait {
            type string;
          }
        }
        leaf shutdown {
          // NCS drop default statement
          type string;
        }
      }
      list ospf {
        // NCS patched for predictable order
        ordered-by user;
        key "ospf-instance";
        leaf ospf-instance {
          type string;
        }
        leaf router-id {
          // NCS drop default statement
          type string;
        }
        leaf advertise-tunnel-link {
          type empty;
        }
        list area {
          // NCS patched for predictable order
          ordered-by user;
          key "area-id";
          leaf area-id {
            type string;
          }
          container nssa {
            leaf area-range {
              type empty;
            }
          }
          list interface {
            // NCS patched for predictable order
            ordered-by user;
            // NCS drop tailf-common:cli-diff-dependency statement
            key "name";
            leaf name {
              type string;
            }
            leaf passive {
              // NCS drop default statement
              type string;
            }
            container message-digest-key {
              leaf key {
                type string;
              }
              leaf md5 {
                type empty;
              }
              leaf hash-value {
                type string;
              }
              leaf hash2 {
                type empty;
              }
            }
            leaf interface-type {
              type string;
            }
            leaf metric {
              type string;
            }
            leaf authentication-type {
              type string;
            }
            leaf bfd-enable {
              type empty;
            }
            leaf shutdown {
              // NCS drop default statement
              type string;
            }
          }
        }
        leaf asbr {
          type empty;
        }
        leaf compatible-rfc1583 {
          type empty;
        }
        leaf disable-ldp-sync {
          type empty;
        }
        leaf-list export {
          // NCS patched for predictable order
          ordered-by user;
          type string;
        }
        container export-limit {
          leaf limit {
            type string;
          }
          leaf log {
            type string;
          }
        }
        container external-db-overflow {
          leaf limit {
            type string;
          }
          leaf seconds {
            type string;
          }
        }
        leaf external-preference {
          type string;
        }
        container graceful-restart {
          leaf helper-disable {
            type empty;
          }
        }
        leaf ldp-over-rsvp {
          type empty;
        }
        leaf multicast-import {
          type empty;
        }
        leaf overload {
          type string;
        }
        leaf overload-include-stub {
          type empty;
        }
        container overload-on-boot {
          presence "true";
          leaf timeout {
            type string;
          }
        }
        leaf preference {
          type string;
        }
        leaf reference-bandwidth {
          type string;
        }
        leaf rsvp-shortcut {
          type empty;
        }
        container timers {
          leaf lsa-arrival {
            type string;
          }
          leaf lsa-generate {
            type string;
          }
          leaf spf-wait {
            type string;
          }
        }
        leaf traffic-engineering {
          type empty;
        }
        leaf unicast-import-disable {
          type empty;
        }
        leaf shutdown {
          // NCS drop default statement
          type string;
        }
      }
      container ospf3 {
        presence "present";
        list area {
          // NCS patched for predictable order
          ordered-by user;
          key "area-id";
          leaf area-id {
            type string;
          }
          list interface {
            // NCS patched for predictable order
            ordered-by user;
            key "interface-name";
            leaf interface-name {
              type string;
            }
            leaf interface-type {
              type string;
            }
            leaf passive {
              type empty;
            }
            leaf shutdown {
              // NCS drop default statement
              type string;
            }
          }
        }
        leaf shutdown {
          // NCS drop default statement
          type string;
        }
      }
      container msdp {
        container local-address {
          leaf group {
            type empty;
          }
        }
      }
      container l2tp {
        leaf shutdown {
          // NCS drop default statement
          type string;
        }
      }
      container ldp {
        presence "present";
        container aggregate-prefix-match {
          leaf shutdown {
            // NCS drop default statement
            type string;
          }
        }
        container interface-parameters {
          list interface {
            // NCS patched for predictable order
            ordered-by user;
            key "name";
            leaf name {
              type string;
            }
            leaf shutdown {
              // NCS drop default statement
              type string;
            }
          }
          container hello {
            leaf timeout {
              type string;
            }
            leaf factor {
              type string;
            }
          }
        }
        leaf prefer-tunnel-in-tunnel {
          type empty;
        }
        container targeted-session {
          leaf hello {
            type empty;
          }
          list peer {
            // NCS patched for predictable order
            ordered-by user;
            key "peer-address";
            leaf peer-address {
              type string;
            }
            leaf bfd-enable {
              type empty;
            }
            container hello {
              leaf timeout {
                type string;
              }
              leaf factor {
                type string;
              }
            }
            container keepalive {
              leaf timeout {
                type string;
              }
              leaf factor {
                type string;
              }
            }
            leaf local-lsr-id {
              type string;
            }
            leaf shutdown {
              // NCS drop default statement
              type string;
            }
          }
        }
        leaf label-withdrawal-delay {
          type string;
        }
        leaf shutdown {
          // NCS drop default statement
          type string;
        }
      }
      container dhcp {
        list local-dhcp-server {
          // NCS patched for predictable order
          ordered-by user;
          key "id";
          leaf id {
            type string;
          }
        }
      }
      list interface {
        // NCS patched for predictable order
        ordered-by user;
        // NCS drop tailf-common:cli-diff-dependency statement
        // NCS drop tailf-common:cli-diff-dependency statement
        key "interface-name";
        leaf interface-name {
          type string;
        }
        leaf address {
          type string;
        }
        leaf description {
          type string;
        }
        leaf ldp-sync-time {
          type string;
        }
        leaf cpu-protection {
          type string;
        }
        leaf loopback {
          type empty;
        }
        leaf unnumbered-mpls-tp {
          type empty;
        }
        leaf port {
          // NCS drop tailf-common:cli-diff-dependency statement
          type string;
        }
        container icmp {
          container redirects {
            leaf a {
              type string;
            }
            leaf b {
              type string;
            }
          }
          container unreachables {
            leaf a {
              type string;
            }
            leaf b {
              type string;
            }
          }
          container ttl-expired {
            leaf a {
              type string;
            }
            leaf b {
              type string;
            }
          }
        }
        leaf qos {
          // NCS drop tailf-common:cli-diff-dependency statement
          type string;
        }
        container ipv6 {
          list address {
            // NCS patched for predictable order
            ordered-by user;
            key "addr";
            leaf addr {
              type string;
            }
            leaf eui-64 {
              type empty;
            }
            leaf preferred {
              type empty;
            }
          }
          container bfd {
            leaf id {
              type string;
            }
            leaf receive {
              type string;
            }
            leaf multiplier {
              type string;
            }
            leaf type {
              type string;
            }
          }
        }
        container bfd {
          leaf id {
            type string;
          }
          leaf receive {
            type string;
          }
          leaf multiplier {
            type string;
          }
          leaf type {
            type string;
          }
        }
        leaf autonomous-system {
          type string;
        }
        leaf shutdown {
          // NCS drop default statement
          type string;
        }
      }
      container mpls {
        presence "true";
        leaf resignal-timer {
          type string;
        }
        container srlg-frr {
          presence "present";
          leaf strict {
            type empty;
          }
        }
        list interface {
          // NCS patched for predictable order
          ordered-by user;
          key "name";
          leaf name {
            type string;
          }
          leaf shutdown {
            // NCS drop default statement
            type string;
          }
        }
        list path {
          // NCS patched for predictable order
          ordered-by user;
          key "name";
          leaf name {
            type string;
          }
          leaf shutdown {
            // NCS drop default statement
            type string;
          }
        }
        list lsp-template {
          // NCS patched for predictable order
          ordered-by user;
          key "template";
          leaf template {
            type string;
          }
          leaf p2mp {
            type empty;
          }
          leaf default-path {
            type string;
          }
          container fast-reroute {
            leaf frr-method {
              type string;
            }
            leaf hop-limit {
              type empty;
            }
          }
          leaf shutdown {
            // NCS drop default statement
            type string;
          }
        }
        list lsp {
          // NCS patched for predictable order
          ordered-by user;
          key "name";
          leaf name {
            type string;
          }
          leaf bypass-only {
            type empty;
          }
          leaf p2mp-lsp {
            type empty;
          }
          leaf mpls-tp {
            type string;
          }
          leaf to {
            type string;
          }
          container fast-reroute {
            leaf frr-method {
              type string;
            }
            leaf hop-limit {
              type empty;
            }
            leaf node-protect {
              type empty;
            }
          }
          container primary {
            leaf path {
              type string;
            }
            leaf adaptive {
              type empty;
            }
          }
          container secondary {
            leaf path {
              type string;
            }
            leaf adaptive {
              type empty;
            }
          }
          leaf cspf {
            type empty;
          }
          leaf shutdown {
            type empty;
          }
        }
        list static-lsp {
          // NCS patched for predictable order
          ordered-by user;
          key "name";
          leaf name {
            type string;
          }
          container push {
            leaf label {
              type string;
            }
            leaf nexthop {
              type string;
            }
          }
          leaf to {
            type string;
          }
          leaf shutdown {
            // NCS drop default statement
            type string;
          }
        }
        leaf shutdown {
          // NCS drop default statement
          type string;
        }
      }
      container rsvp {
        // NCS drop tailf-common:cli-diff-dependency statement
        // NCS drop must statement
        presence "present";
        list interface {
          // NCS patched for predictable order
          ordered-by user;
          // NCS drop tailf-common:cli-diff-dependency statement
          key "name";
          leaf name {
            type string;
          }
          container refresh-reduction {
            leaf reliable-delivery {
              type empty;
            }
          }
          container authentication-key {
            leaf key {
              type string;
            }
            leaf type {
              type string;
            }
          }
          leaf shutdown {
            // NCS drop default statement
            type string;
          }
        }
        leaf shutdown {
          // NCS drop default statement
          type string;
        }
      }
      container router-advertisement {
        // NCS drop tailf-common:cli-diff-dependency statement
        list interface {
          // NCS patched for predictable order
          ordered-by user;
          key "ip-int-name";
          leaf ip-int-name {
            type string;
          }
          leaf current-hop-limit {
            type string;
          }
          leaf max-advertisement-interval {
            type string;
          }
          leaf min-advertisement-interval {
            type string;
          }
          leaf mtu {
            type string;
          }
          leaf managed-configuration {
            type empty;
          }
          leaf other-stateful-configuration {
            type empty;
          }
          list prefix {
            // NCS patched for predictable order
            ordered-by user;
            key "ipv6-prefix";
            leaf ipv6-prefix {
              type string;
            }
          }
          leaf reachable-time {
            type string;
          }
          leaf retransmit-time {
            type string;
          }
          leaf router-lifetime {
            type string;
          }
          leaf use-virtual-mac {
            type empty;
          }
          leaf shutdown {
            // NCS drop default statement
            type string;
          }
        }
      }
      container mld {
        // NCS drop tailf-common:cli-diff-dependency statement
        list interface {
          // NCS patched for predictable order
          ordered-by user;
          key "ip-int-name";
          leaf ip-int-name {
            type string;
          }
          leaf shutdown {
            // NCS drop default statement
            type string;
          }
        }
        leaf shutdown {
          // NCS drop default statement
          type string;
        }
      }
      container policy-options {
        container begin {
          list prefix-list {
            // NCS patched for predictable order
            ordered-by user;
            key "name";
            leaf name {
              type string;
            }
            list prefix {
              // NCS patched for predictable order
              ordered-by user;
              key "ip-prefix";
              leaf ip-prefix {
                type string;
              }
              choice a {
                leaf exact {
                  type empty;
                }
                leaf longer {
                  type empty;
                }
                leaf through {
                  type string;
                }
                leaf prefix-length-range {
                  type string;
                }
              }
            }
          }
          list community {
            // NCS patched for predictable order
            ordered-by user;
            key "name";
            leaf name {
              type string;
            }
            choice community-choice {
              case a {
                leaf-list members {
                  // NCS patched for predictable order
                  ordered-by user;
                  type string;
                }
              }
              case b {
                leaf expression {
                  type string;
                }
              }
            }
          }
          list damping {
            // NCS patched for predictable order
            ordered-by user;
            key "name";
            leaf name {
              type string;
            }
            leaf half-life {
              type string;
            }
            leaf max-suppress {
              type string;
            }
            leaf reuse {
              type string;
            }
            leaf suppress {
              type string;
            }
          }
          list policy-statement {
            // NCS patched for predictable order
            ordered-by user;
            key "name";
            leaf name {
              type string;
            }
            container default-action {
              uses ncs_template_policy-options-action-grouping;
            }
            list entry {
              // NCS patched for predictable order
              ordered-by user;
              key "id";
              leaf id {
                type string;
              }
              leaf description {
                type string;
              }
              container action {
                uses ncs_template_policy-options-action-grouping;
              }
              container from {
                leaf area {
                  type string;
                }
                leaf as-path {
                  type string;
                }
                leaf as-path-group {
                  type string;
                }
                leaf community {
                  type string;
                }
                leaf external {
                  type empty;
                }
                leaf-list family {
                  // NCS patched for predictable order
                  ordered-by user;
                  type string;
                }
                leaf group-address {
                  type string;
                }
                leaf host-ip {
                  type string;
                }
                leaf interface {
                  type string;
                }
                leaf level {
                  type string;
                }
                container neighbor {
                  choice a {
                    leaf ip-address {
                      type string;
                    }
                    leaf prefix-list {
                      type string;
                    }
                  }
                }
                leaf origin {
                  type string;
                }
                leaf policy {
                  type string;
                }
                leaf-list prefix-list {
                  // NCS patched for predictable order
                  ordered-by user;
                  type string;
                }
                leaf protocol {
                  type string;
                }
                leaf source-address {
                  type string;
                }
                leaf state {
                  type string;
                }
                leaf tag {
                  type string;
                }
                leaf type {
                  type string;
                }
              }
              container to {
                leaf level {
                  type string;
                }
                leaf neighbor {
                  type string;
                }
                leaf-list prefix-list {
                  // NCS patched for predictable order
                  ordered-by user;
                  type string;
                }
                leaf protocol {
                  type string;
                }
              }
            }
          }
          list as-path {
            // NCS patched for predictable order
            ordered-by user;
            key "name";
            leaf name {
              type string;
            }
            leaf regexp {
              type string;
            }
          }
        }
      }
      container pim {
        presence "present";
        list interface {
          // NCS patched for predictable order
          ordered-by user;
          key "ip-int-name";
          leaf ip-int-name {
            type string;
          }
          leaf assert-period {
            type string;
          }
          leaf bfd-enable {
            type string;
          }
          leaf bsm-check-rtr-alert {
            type empty;
          }
          leaf hello-interval {
            type string;
          }
          leaf hello-multiplier {
            type string;
          }
          leaf improved-assert {
            type empty;
          }
          leaf instant-prune-echo {
            type empty;
          }
          leaf ipv4-multicast-disable {
            type empty;
          }
          leaf ipv6-multicast-disable {
            type empty;
          }
          leaf max-groups {
            type string;
          }
          container mcac {
            container mc-constraints {
              container level {
                leaf level-id {
                  type string;
                }
                leaf bw {
                  type string;
                }
              }
              list number-down {
                // NCS patched for predictable order
                ordered-by user;
                key "number-lag-port-down";
                leaf number-lag-port-down {
                  type string;
                }
                leaf level-id {
                  type string;
                }
              }
              leaf use-lag-port-weight {
                type empty;
              }
              leaf shutdown {
                // NCS drop default statement
                type string;
              }
            }
            leaf policy {
              type string;
            }
            container unconstrained-bw {
              leaf bandwidth {
                type string;
              }
              leaf mandatory-bw {
                type string;
              }
            }
          }
          leaf multicast-senders {
            type string;
          }
          leaf p2mp-ldp-tree-join {
            type string;
          }
          leaf priority {
            type string;
          }
          container sticky-dr {
            leaf priority {
              type string;
            }
            leaf three-way-hello {
              type empty;
            }
            leaf tracking-support {
              type empty;
            }
          }
          leaf shutdown {
            // NCS drop default statement
            type string;
          }
        }
        leaf ipv4-multicast-disable {
          type empty;
        }
        leaf ipv6-multicast-disable {
          type empty;
        }
        container rp {
          list anycast {
            // NCS patched for predictable order
            ordered-by user;
            key "rp-ip-address";
            leaf rp-ip-address {
              type string;
            }
            list rp-set-peer {
              // NCS patched for predictable order
              ordered-by user;
              key "ip-address";
              leaf ip-address {
                type string;
              }
            }
          }
          container static {
            presence "true";
            list address {
              // NCS patched for predictable order
              ordered-by user;
              key "ip-address";
              leaf ip-address {
                type string;
              }
              list group-prefix {
                // NCS patched for predictable order
                ordered-by user;
                key "grp-ip-addr";
                leaf grp-ip-addr {
                  type string;
                }
              }
            }
          }
          container bsr-candidate {
            leaf shutdown {
              // NCS drop default statement
              type string;
            }
          }
          container rp-candidate {
            leaf shutdown {
              // NCS drop default statement
              type string;
            }
          }
        }
        leaf shutdown {
          // NCS drop default statement
          type string;
        }
      }
    }
    container system {
      container alarms {
        leaf max-cleared {
          type string;
        }
        leaf shutdown {
          // NCS drop default statement
          type string;
        }
      }
      container atm {
        leaf atm-location-id {
          type string;
        }
        container oam {
          leaf loopback-period {
            type string;
          }
          leaf retry-down {
            type string;
          }
          leaf retry-up {
            type string;
          }
        }
      }
      leaf boot-bad-exec {
        type string;
      }
      leaf boot-good-exec {
        type string;
      }
      list chassis-mode {
        // NCS patched for predictable order
        ordered-by user;
        key "chassis-mode";
        leaf chassis-mode {
          type string;
        }
        leaf force {
          type empty;
        }
        list power-supply {
          // NCS patched for predictable order
          ordered-by user;
          key "power-supply-id power-supply-type";
          leaf power-supply-id {
            type string;
          }
          leaf power-supply-type {
            type string;
          }
        }
      }
      leaf clli-code {
        type string;
      }
      leaf config-backup {
        type string;
      }
      leaf contact {
        type string;
      }
      leaf coordinates {
        type string;
      }
      container dns {
        container address-pref {
          choice choice {
            leaf ipv4-only {
              type empty;
            }
            leaf ipv6-first {
              type empty;
            }
          }
        }
      }
      leaf enable-icmp-vse {
        type empty;
      }
      container ethernet {
        container efm-oam {
          leaf grace-tx-enable {
            type empty;
          }
        }
        leaf new-qinq-untagged-sap {
          type empty;
        }
      }
      leaf l4-load-balancing {
        type empty;
      }
      leaf lacp-system-priority {
        type string;
      }
      container lldp {
        leaf message-fast-tx {
          type string;
        }
        leaf message-fast-tx-init {
          type string;
        }
        leaf reinit-delay {
          type string;
        }
        leaf tx-credit-max {
          type string;
        }
        leaf tx-hold-multiplier {
          type string;
        }
        leaf tx-interval {
          type string;
        }
        leaf notification-interval {
          type string;
        }
        leaf shutdown {
          // NCS drop default statement
          type string;
        }
      }
      leaf location {
        type string;
      }
      container login-control {
        leaf exponential-backoff {
          type empty;
        }
        container ftp {
          leaf inbound-max-sessions {
            type string;
          }
        }
        leaf idle-timeout {
          type string;
        }
        leaf idle-timeoutdisable {
          type empty;
        }
        leaf login-banner {
          type empty;
        }
        container motd {
          choice choice {
            leaf url {
              type string;
            }
            leaf text {
              type string;
            }
          }
        }
        container pre-login-message {
          presence "present";
          leaf login-text-string {
            type string;
          }
          leaf name {
            type empty;
          }
        }
        container ssh {
          leaf disable-graceful-shutdown {
            type empty;
          }
          leaf inbound-max-sessions {
            type string;
          }
          leaf outbound-max-sessions {
            type string;
          }
          leaf ttl-security {
            type string;
          }
        }
        container telnet {
          leaf enable-graceful-shutdown {
            type empty;
          }
          leaf inbound-max-sessions {
            type string;
          }
          leaf outbound-max-sessions {
            type string;
          }
          leaf ttl-security {
            type string;
          }
        }
      }
      container lsr-load-balancing {
        choice choice {
          leaf lbl-only {
            type empty;
          }
          leaf lbl-ip {
            type empty;
          }
          leaf ip-only {
            type empty;
          }
        }
      }
      leaf mc-enh-load-balancing {
        type empty;
      }
      leaf mixed-mode {
        type empty;
      }
      leaf name {
        type string;
      }
      container netconf {
        leaf shutdown {
          // NCS drop default statement
          type string;
        }
      }
      container persistence {
        container ancp {
          leaf description {
            type string;
          }
          leaf location {
            type string;
          }
        }
        container application-assurance {
          leaf description {
            type string;
          }
          leaf location {
            type string;
          }
        }
        container dhcp-server {
          leaf description {
            type string;
          }
          leaf location {
            type string;
          }
        }
        container nat-port-forwarding {
          leaf description {
            type string;
          }
          leaf location {
            type string;
          }
        }
        container subscriber-mgmt {
          leaf description {
            type string;
          }
          leaf location {
            type string;
          }
        }
      }
      container snmp {
        leaf engineID {
          type string;
        }
        leaf general-port {
          type string;
        }
        leaf packet-size {
          type string;
        }
        leaf shutdown {
          // NCS drop default statement
          type string;
        }
      }
      container rollback {
        leaf local-max-checkpoints {
          type string;
        }
        leaf remote-max-checkpoints {
          type string;
        }
        leaf rescue-location {
          type string;
        }
        leaf rollback-location {
          type string;
        }
      }
      container time {
        container ntp {
          leaf authentication-check {
            type empty;
          }
          list authentication-key {
            // NCS patched for predictable order
            ordered-by user;
            key "key-id";
            leaf key-id {
              type string;
            }
            leaf key {
              type string;
            }
            leaf hash {
              type string;
            }
            leaf type {
              type string;
            }
          }
          list server {
            // NCS patched for predictable order
            ordered-by user;
            key "address";
            leaf address {
              type string;
            }
            leaf key-id {
              type string;
            }
            leaf version {
              type string;
            }
            leaf prefer {
              type empty;
            }
          }
          leaf shutdown {
            // NCS drop default statement
            type string;
          }
        }
        container sntp {
          leaf broadcast-client {
            type empty;
          }
          container server-address {
            leaf ip {
              type string;
            }
            leaf version {
              type string;
            }
            leaf mode {
              type string;
            }
            leaf interval {
              type string;
            }
          }
          leaf shutdown {
            // NCS drop default statement
            type string;
          }
        }
        container zone {
          leaf name {
            type string;
          }
          leaf time {
            type string;
          }
        }
        container dst-zone {
          leaf name {
            type string;
          }
          container start {
            uses ncs_template_time-stamp;
          }
          container end {
            uses ncs_template_time-stamp;
          }
        }
      }
      container thresholds {
        container rmon {
          leaf alarm {
            type empty;
          }
          leaf event {
            type empty;
          }
        }
      }
      list power-supply {
        // NCS patched for predictable order
        ordered-by user;
        key "power-supply-id";
        leaf power-supply-id {
          type string;
        }
      }
      container security {
        container hash-control {
          leaf read-version {
            type string;
          }
          leaf write-version {
            type string;
          }
        }
        list profile {
          // NCS patched for predictable order
          ordered-by user;
          key "name";
          leaf name {
            type string;
          }
          leaf default-action {
            type string;
          }
          list entry {
            // NCS patched for predictable order
            ordered-by user;
            key "entry-id";
            leaf entry-id {
              type string;
            }
            leaf action {
              type string;
            }
            leaf description {
              type string;
            }
            leaf match {
              type string;
            }
          }
        }
        container password {
          leaf health-check {
            type string;
          }
          leaf-list authentication-order {
            // NCS patched for predictable order
            ordered-by user;
            type string;
          }
          container attempts {
            leaf count {
              type string;
            }
            leaf time {
              type string;
            }
            leaf lockout {
              type string;
            }
          }
        }
        container radius {
          leaf authorization {
            type empty;
          }
          leaf accounting {
            type empty;
          }
          list server {
            // NCS patched for predictable order
            ordered-by user;
            key "server-index";
            leaf server-index {
              type string;
            }
            leaf address {
              // NCS drop mandatory statement
              type string;
            }
            leaf secret {
              // NCS drop mandatory statement
              type string;
            }
            leaf type {
              // NCS drop mandatory statement
              type string;
            }
          }
        }
        container tacplus {
          container accounting {
            leaf record-type {
              type string;
            }
          }
          container authorization {
            presence "true";
            leaf use-prix-lvl {
              type empty;
            }
          }
          leaf interactive-authentication {
            type empty;
          }
          container priv-lvl-map {
            list priv-lvl {
              // NCS patched for predictable order
              ordered-by user;
              key "lvl";
              leaf lvl {
                type string;
              }
              leaf user-profile {
                type string;
              }
            }
          }
          list server {
            // NCS patched for predictable order
            ordered-by user;
            key "server-index";
            leaf server-index {
              type string;
            }
            leaf address {
              type string;
            }
            leaf secret {
              type string;
            }
            leaf hash {
              // NCS drop default statement
              type string;
            }
            leaf port {
              type string;
            }
          }
          leaf timeout {
            type string;
          }
          leaf use-default-template {
            type empty;
          }
          leaf shutdown {
            // NCS drop default statement
            type string;
          }
        }
        leaf telnet-server {
          type empty;
        }
        leaf telnet6-server {
          type empty;
        }
        leaf ftp-server {
          type empty;
        }
        leaf per-peer-queuing {
          type empty;
        }
        container snmp {
          container access {
            list group {
              // NCS patched for predictable order
              ordered-by user;
              key "name";
              leaf name {
                type string;
              }
              leaf security-model {
                type string;
              }
              leaf security-level {
                type string;
              }
              leaf read {
                type string;
              }
              leaf notify {
                type string;
              }
            }
          }
          list community {
            // NCS patched for predictable order
            ordered-by user;
            key "name";
            leaf name {
              type string;
            }
            leaf type {
              // NCS drop default statement
              type string;
            }
            leaf access-parameters {
              type string;
            }
            leaf version {
              type string;
            }
            leaf src-access-list {
              type string;
            }
          }
        }
        container source-address {
          list application {
            // NCS patched for predictable order
            ordered-by user;
            key "name";
            leaf name {
              type string;
            }
            leaf address {
              type string;
            }
          }
        }
        container ssh {
          leaf preserve-key {
            type empty;
          }
          leaf server-shutdown {
            type empty;
          }
          leaf version {
            type string;
          }
        }
        list user {
          // NCS patched for predictable order
          ordered-by user;
          key "user-id";
          leaf user-id {
            type string;
          }
          leaf-list access {
            // NCS patched for predictable order
            ordered-by user;
            type string;
          }
          container console {
            leaf cannot-change-password {
              type empty;
            }
            leaf login-exec {
              type string;
            }
            list member {
              // NCS patched for predictable order
              ordered-by user;
              key "name";
              leaf name {
                type string;
              }
            }
            leaf new-password-at-login {
              type empty;
            }
          }
          leaf home-directory {
            type string;
          }
          container password {
            leaf id {
              type string;
            }
            leaf method {
              type string;
            }
          }
          leaf restricted-to-home {
            type empty;
          }
          container snmp {
            container authentication {
              leaf hash {
                type string;
              }
              leaf key-1 {
                type string;
              }
              leaf privacy {
                type string;
              }
              leaf key-2 {
                type string;
              }
              leaf hashval {
                type string;
              }
            }
            leaf group {
              type string;
            }
          }
        }
        container cpu-protection {
          leaf link-specific-rate {
            type string;
          }
          list policy {
            // NCS patched for predictable order
            ordered-by user;
            key "policy-id";
            leaf policy-id {
              type string;
            }
            leaf overall-rate {
              type string;
            }
          }
          leaf protocol-protection {
            type empty;
          }
          leaf port-overall-rate {
            type string;
          }
        }
        container cpm-filter {
          leaf default-action {
            type string;
          }
          container ip-filter {
            list entry {
              // NCS patched for predictable order
              ordered-by user;
              key "entry-id";
              leaf entry-id {
                type string;
              }
              container action {
                choice action-choice {
                  leaf drop {
                    type empty;
                  }
                  leaf accept {
                    type empty;
                  }
                  leaf queue {
                    type string;
                  }
                }
              }
              leaf description {
                type string;
              }
              leaf log {
                type string;
              }
              container match {
                leaf protocol {
                  type ncs_template_protocol;
                }
                leaf dscp {
                  type ncs_template_dscp-type;
                }
                container dst-ip {
                  uses ncs_template_filter-match-ip-grouping;
                }
                container dst-port {
                  uses ncs_template_cpm-filter-match-port-grouping;
                }
                leaf fragment {
                  type string;
                }
                leaf icmp-code {
                  type string;
                }
                leaf icmp-type {
                  type ncs_template_icmp-type;
                }
                container ip-option {
                  leaf value {
                    type string;
                  }
                  leaf mask {
                    type string;
                  }
                }
                leaf multiple-option {
                  type string;
                }
                leaf option-present {
                  type string;
                }
                container port {
                  uses ncs_template_cpm-filter-match-port-grouping;
                }
                leaf router {
                  type string;
                }
                container src-ip {
                  uses ncs_template_filter-match-ip-grouping;
                }
                container src-port {
                  uses ncs_template_cpm-filter-match-port-grouping;
                }
                leaf tcp-ack {
                  type string;
                }
                leaf tcp-syn {
                  type string;
                }
              }
            }
            leaf shutdown {
              // NCS drop default statement
              type string;
            }
          }
          container ipv6-filter {
            list entry {
              // NCS patched for predictable order
              ordered-by user;
              key "entry-id";
              leaf entry-id {
                type string;
              }
              container action {
                choice action-choice {
                  leaf drop {
                    type empty;
                  }
                  leaf accept {
                    type empty;
                  }
                  leaf queue {
                    type string;
                  }
                }
              }
              leaf description {
                type string;
              }
              leaf log {
                type string;
              }
              container match {
                leaf next-header {
                  type ncs_template_protocol;
                }
                leaf dscp {
                  type ncs_template_dscp-type;
                }
                leaf dst-ip {
                  type string;
                }
                container dst-port {
                  uses ncs_template_cpm-filter-match-port-grouping;
                }
                leaf flow-label {
                  type string;
                }
                leaf hop-by-hop-opt {
                  type string;
                }
                leaf icmp-code {
                  type string;
                }
                leaf icmp-type {
                  type ncs_template_icmpv6-type;
                }
                container port {
                  uses ncs_template_cpm-filter-match-port-grouping;
                }
                leaf router {
                  type string;
                }
                container src-ip {
                  uses ncs_template_filter-match-ipv6-grouping;
                }
                container src-port {
                  uses ncs_template_cpm-filter-match-port-grouping;
                }
                leaf tcp-ack {
                  type string;
                }
                leaf tcp-syn {
                  type string;
                }
              }
            }
            leaf shutdown {
              // NCS drop default statement
              type string;
            }
          }
        }
        container cpm-queue {
          list queue {
            // NCS patched for predictable order
            ordered-by user;
            key "queue-id";
            leaf queue-id {
              type string;
            }
            container rate {
              leaf value {
                type string;
              }
              leaf cir {
                type string;
              }
            }
          }
        }
        container management-access-filter {
          container ip-filter {
            leaf default-action {
              type ncs_template_filter-action;
            }
            list entry {
              // NCS patched for predictable order
              ordered-by user;
              key "entry-name";
              leaf entry-name {
                type string;
              }
              leaf action {
                type ncs_template_filter-action;
              }
              leaf description {
                type string;
              }
              leaf src-ip {
                type string;
              }
              leaf dst-port {
                type string;
              }
              leaf src-port {
                type string;
              }
              leaf router {
                type string;
              }
            }
            leaf shutdown {
              // NCS drop default statement
              type string;
            }
          }
          container ipv6-filter {
            leaf default-action {
              type ncs_template_filter-action;
            }
            list entry {
              // NCS patched for predictable order
              ordered-by user;
              key "entry-name";
              leaf entry-name {
                type string;
              }
              leaf action {
                type ncs_template_filter-action;
              }
              leaf description {
                type string;
              }
              leaf src-ip {
                type string;
              }
              leaf dst-port {
                type string;
              }
              leaf src-port {
                type string;
              }
            }
            leaf shutdown {
              // NCS drop default statement
              type string;
            }
          }
        }
        leaf vprn-network-exceptions {
          type empty;
        }
      }
      container sync-if-timing {
        container begin {
          leaf description {
            type string;
          }
        }
      }
    }
    container redundancy {
      container multi-chassis {
        list peer {
          // NCS patched for predictable order
          ordered-by user;
          key "address";
          leaf address {
            type string;
          }
          container mc-lag {
            leaf shutdown {
              // NCS drop default statement
              type string;
            }
          }
          leaf shutdown {
            // NCS drop default statement
            type string;
          }
        }
      }
      leaf synchronize {
        type string;
      }
    }
    container filter {
      list ip-filter {
        // NCS patched for predictable order
        ordered-by user;
        key "ip-filter-name";
        leaf ip-filter-name {
          type string;
        }
        list embed-filter {
          // NCS patched for predictable order
          ordered-by user;
          key "embed-filter-name";
          leaf embed-filter-name {
            type string;
          }
          leaf offset {
            type string;
          }
          leaf status {
            type string;
          }
        }
        leaf default-action {
          type string;
        }
        leaf scope {
          type string;
        }
        leaf description {
          type string;
        }
        list entry {
          // NCS patched for predictable order
          ordered-by user;
          uses ncs_template_ip-filter-entry-grouping;
          key "entry-name";
          container action {
            choice action-choice {
              case aa {
                leaf drop {
                  type empty;
                }
              }
              case ab {
                leaf nat {
                  type empty;
                }
              }
              case ac {
                leaf http-redirect {
                  type string;
                }
              }
              case ad {
                container forward {
                  presence "true";
                  container next-hop {
                    choice next-hop-choice {
                      case na {
                        leaf ip-address {
                          type string;
                        }
                      }
                      case nb {
                        leaf indirect {
                          type string;
                        }
                      }
                      case nc {
                        leaf interface {
                          type string;
                        }
                      }
                    }
                  }
                  leaf sap {
                    type string;
                  }
                  leaf sdp {
                    type string;
                  }
                  leaf redirect-policy {
                    type string;
                  }
                }
              }
            }
          }
        }
      }
      list ipv6-filter {
        // NCS patched for predictable order
        ordered-by user;
        key "ip-filter-name";
        leaf ip-filter-name {
          type string;
        }
        leaf default-action {
          type string;
        }
        list embed-filter {
          // NCS patched for predictable order
          ordered-by user;
          key "embed-filter-name";
          leaf embed-filter-name {
            type string;
          }
          leaf offset {
            type string;
          }
          leaf status {
            type string;
          }
        }
        leaf scope {
          type string;
        }
        leaf description {
          type string;
        }
        list entry {
          // NCS patched for predictable order
          ordered-by user;
          uses ncs_template_ipv6-filter-entry-grouping;
          key "entry-name";
          leaf action {
            type string;
          }
        }
      }
      list mac-filter {
        // NCS patched for predictable order
        ordered-by user;
        key "mac-filter-name";
        leaf mac-filter-name {
          type string;
        }
        leaf default-action {
          type string;
        }
        leaf scope {
          type string;
        }
        leaf description {
          type string;
        }
        list entry {
          // NCS patched for predictable order
          ordered-by user;
          key "entry-name";
          leaf entry-name {
            type string;
          }
          leaf description {
            type string;
          }
          container match {
            container dst-mac {
              leaf mac {
                type string;
              }
              leaf mask {
                type string;
              }
            }
            container src-mac {
              leaf mac {
                type string;
              }
              leaf mask {
                type string;
              }
            }
            leaf frame-type {
              type string;
            }
            leaf etype {
              // NCS drop when statement
              type string;
            }
          }
          container action {
            choice choice {
              case drop {
                leaf drop {
                  type empty;
                }
              }
              case forward {
                leaf forward {
                  type empty;
                }
                leaf sap {
                  type string;
                }
              }
            }
          }
          leaf log {
            type string;
          }
        }
      }
      container match-list {
        list ip-prefix-list {
          // NCS patched for predictable order
          ordered-by user;
          key "name";
          leaf name {
            type string;
          }
          leaf description {
            type string;
          }
          list prefix {
            // NCS patched for predictable order
            ordered-by user;
            key "pfx";
            leaf pfx {
              type string;
            }
          }
        }
        list ipv6-prefix-list {
          // NCS patched for predictable order
          ordered-by user;
          key "name";
          leaf name {
            type string;
          }
          leaf description {
            type string;
          }
          list prefix {
            // NCS patched for predictable order
            ordered-by user;
            key "pfx";
            leaf pfx {
              type string;
            }
          }
        }
      }
      list log {
        // NCS patched for predictable order
        ordered-by user;
        key "log-id";
        leaf log-id {
          type string;
        }
        leaf description {
          type string;
        }
        container destination {
          choice choice {
            leaf memory {
              type string;
            }
            leaf syslog {
              type string;
            }
          }
        }
      }
    }
    container test-oam {
      container twamp {
        container server {
          leaf inactivity-timeout {
            type string;
            // NCS drop default statement
          }
          leaf max-conn-server {
            type string;
            // NCS drop default statement
          }
          leaf max-sess-server {
            type string;
            // NCS drop default statement
          }
          list prefix {
            // NCS patched for predictable order
            ordered-by user;
            key "ip-prefix";
            leaf ip-prefix {
              type string;
            }
            leaf description {
              type string;
            }
            leaf max-conn-prefix {
              type string;
              // NCS drop default statement
            }
            leaf max-sess-prefix {
              type string;
              // NCS drop default statement
            }
          }
          leaf shutdown {
            // NCS drop default statement
            type string;
          }
        }
      }
    }
    container mirror {
      list mirror-dest {
        // NCS patched for predictable order
        ordered-by user;
        key "service-id";
        leaf service-id {
          type string;
        }
        leaf mirror-type {
          type string;
        }
        leaf type {
          type string;
        }
        leaf description {
          type string;
        }
        leaf enable-port-id {
          type empty;
        }
        container encap {
          list layer-3-encap {
            // NCS patched for predictable order
            ordered-by user;
            key "encap";
            // NCS drop max-elements statement
            leaf encap {
              type string;
            }
          }
        }
        list endpoint {
          // NCS patched for predictable order
          ordered-by user;
          key "endpoint-name";
          leaf endpoint-name {
            type string;
          }
          leaf description {
            type string;
          }
          leaf revert-time {
            type string;
          }
        }
        leaf fc {
          type string;
        }
        container isa-aa-group {
          leaf aa-group-id {
            type string;
          }
          leaf traffic-direction {
            type string;
          }
        }
        container remote-source {
          leaf far-end {
            type string;
          }
          list spoke-sdp {
            // NCS patched for predictable order
            ordered-by user;
            key "sdp-id vc-id";
            leaf sdp-id {
              type string;
            }
            leaf vc-id {
              type string;
            }
            leaf endpoint {
              type string;
            }
            leaf shutdown {
              // NCS drop default statement
              type string;
            }
          }
        }
        list sap {
          // NCS patched for predictable order
          ordered-by user;
          key "sap-id";
          leaf sap-id {
            type string;
          }
          container cem {
            container packet {
              leaf jitter-buffer {
                type string;
              }
              leaf bytes {
                type string;
              }
            }
            leaf rtp-header {
              type empty;
            }
          }
          container egress {
            container ip-mirror {
              leaf sa-mac {
                type ncs_template_ieee-mac;
              }
            }
            leaf qos {
              type string;
            }
          }
        }
        leaf service-name {
          type string;
        }
        leaf shutdown {
          // NCS drop default statement
          type string;
        }
        leaf slice-size {
          type string;
        }
        list spoke-sdp {
          // NCS patched for predictable order
          ordered-by user;
          key "sdp-id vc-id";
          leaf sdp-id {
            type string;
          }
          leaf vc-id {
            type string;
          }
          leaf endpoint {
            type string;
          }
          leaf control-word {
            type empty;
          }
          leaf precedence {
            type string;
          }
          container egress {
            container l2tpv3 {
              leaf cookie {
                type string;
              }
            }
            leaf vc-label {
              type string;
            }
          }
          container ingress {
            leaf vc-label {
              type string;
            }
          }
          leaf shutdown {
            // NCS drop default statement
            type string;
          }
        }
      }
    }
    container saa {
      list test {
        // NCS patched for predictable order
        ordered-by user;
        key "test-name";
        leaf test-name {
          type string;
        }
        leaf accounting-policy {
          type string;
        }
        leaf continuous {
          type empty;
        }
        leaf description {
          type string;
        }
        container jitter-event {
          leaf rising-threshold {
            type string;
          }
          leaf falling-threshold {
            type string;
          }
        }
        container latency-event {
          leaf rising-threshold {
            type string;
          }
          leaf falling-threshold {
            type string;
          }
        }
        container loss-event {
          leaf rising-threshold {
            type string;
          }
          leaf falling-threshold {
            type string;
          }
        }
        container type {
          container cpe-ping {
            leaf service {
              type string;
            }
            leaf destination {
              type string;
            }
            leaf source {
              type string;
            }
            leaf source-mac {
              type ncs_template_ieee-mac;
            }
            leaf fc {
              type string;
              // NCS drop default statement
            }
            leaf profile {
              type string;
              // NCS drop default statement
            }
            leaf ttl {
              type string;
            }
            leaf count {
              type string;
            }
            leaf send-control {
              type empty;
            }
            leaf return-control {
              type empty;
            }
            leaf interval {
              type string;
            }
          }
          container dns {
            leaf target-addr {
              type string;
            }
            leaf name-server {
              type string;
            }
            leaf source {
              type string;
            }
            leaf count {
              type string;
              // NCS drop default statement
            }
            leaf timeout {
              type string;
              // NCS drop default statement
            }
            leaf interval {
              type string;
              // NCS drop default statement
            }
            leaf record-type {
              type string;
            }
          }
          container eth-cfm-two-way-delay {
            leaf mac-address {
              type ncs_template_ieee-mac;
            }
            leaf mep {
              type string;
            }
            leaf domain {
              type string;
            }
            leaf association {
              type string;
            }
            leaf fc {
              type string;
              // NCS drop default statement
            }
            leaf profile {
              type string;
              // NCS drop default statement
            }
            leaf count {
              type string;
              // NCS drop default statement
            }
            leaf timeout {
              type string;
              // NCS drop default statement
            }
            leaf interval {
              type string;
              // NCS drop default statement
            }
          }
          container lsp-ping {
            leaf lsp-name {
              type string;
            }
            leaf path {
              type string;
            }
            leaf fc {
              type string;
              // NCS drop default statement
            }
            leaf profile {
              type string;
              // NCS drop default statement
            }
            leaf interval {
              type string;
              // NCS drop default statement
            }
            leaf send-count {
              type string;
              // NCS drop default statement
            }
            leaf size {
              type string;
              // NCS drop default statement
            }
            leaf src-ip-address {
              type string;
            }
            leaf timeout {
              type string;
              // NCS drop default statement
            }
            leaf ttl {
              type string;
              // NCS drop default statement
            }
          }
          container sdp-ping {
            leaf orig-sdp-id {
              type string;
            }
            leaf resp-sdp {
              type string;
            }
            leaf fc {
              type string;
              // NCS drop default statement
            }
            leaf profile {
              type string;
              // NCS drop default statement
            }
            leaf size {
              type string;
              // NCS drop default statement
            }
            leaf count {
              type string;
              // NCS drop default statement
            }
            leaf timeout {
              type string;
              // NCS drop default statement
            }
            leaf interval {
              type string;
              // NCS drop default statement
            }
          }
          container vprn-ping {
            leaf service-id {
              type string;
            }
            leaf source {
              type string;
            }
            leaf destination {
              type string;
            }
            leaf fc {
              type string;
              // NCS drop default statement
            }
            leaf profile {
              type string;
              // NCS drop default statement
            }
            leaf size {
              type string;
              // NCS drop default statement
            }
            leaf ttl {
              type string;
            }
            leaf count {
              type string;
            }
            leaf return-control {
              type empty;
            }
            leaf timeout {
              type string;
            }
            leaf interval {
              type string;
            }
          }
        }
        container trap-gen {
          leaf probe-fail-enable {
            type empty;
          }
          leaf probe-fail-threshold {
            type string;
          }
          leaf test-completion-enable {
            type empty;
          }
          leaf test-fail-enable {
            type empty;
          }
          leaf test-fail-threshold {
            type string;
          }
        }
        leaf shutdown {
          // NCS drop default statement
          type string;
        }
      }
    }
    container subscriber-mgmt {
      list authentication-policy {
        // NCS patched for predictable order
        ordered-by user;
        key "name";
        leaf name {
          type string;
        }
        leaf description {
          type string;
        }
        container password {
          leaf pw {
            type string;
          }
          leaf hashing-scheme {
            type string;
          }
        }
      }
      list sla-profile {
        // NCS patched for predictable order
        ordered-by user;
        key "sla-profile-name";
        leaf sla-profile-name {
          type string;
        }
        leaf description {
          type string;
        }
        container ingress {
          list qos {
            // NCS patched for predictable order
            ordered-by user;
            key "id";
            leaf id {
              type string;
            }
            leaf multipoint-shared {
              type empty;
            }
          }
          leaf ip-filter {
            type string;
          }
          leaf ipv6-filter {
            type string;
          }
          leaf qos-marking-from-sap {
            type string;
          }
        }
        container egress {
          list qos {
            // NCS patched for predictable order
            ordered-by user;
            key "id";
            leaf id {
              type string;
            }
            leaf multipoint-shared {
              type empty;
            }
          }
          leaf ip-filter {
            type string;
          }
          leaf ipv6-filter {
            type string;
          }
          leaf qos-marking-from-sap {
            type string;
          }
        }
      }
      list sub-profile {
        // NCS patched for predictable order
        ordered-by user;
        key "sub-profile-name";
        leaf sub-profile-name {
          type string;
        }
        leaf description {
          type string;
        }
        leaf accounting-policy {
          type string;
        }
        leaf collect-stats {
          type empty;
        }
      }
    }
    container debug {
      list mirror-source {
        // NCS patched for predictable order
        ordered-by user;
        key "service-id";
        leaf service-id {
          type string;
        }
        list ingress-label {
          // NCS patched for predictable order
          ordered-by user;
          key "label";
          // NCS drop max-elements statement
          leaf label {
            type string;
          }
        }
        list ip-filter {
          // NCS patched for predictable order
          ordered-by user;
          key "ip-filter-name";
          leaf ip-filter-name {
            type string;
          }
          list entry {
            // NCS patched for predictable order
            ordered-by user;
            key "id";
            // NCS drop max-elements statement
            leaf id {
              type string;
            }
          }
        }
        list mac-filter {
          // NCS patched for predictable order
          ordered-by user;
          key "mac-filter-name";
          leaf mac-filter-name {
            type string;
          }
          list entry {
            // NCS patched for predictable order
            ordered-by user;
            key "id";
            // NCS drop max-elements statement
            leaf id {
              type string;
            }
          }
        }
        list port {
          // NCS patched for predictable order
          ordered-by user;
          key "port-id";
          leaf lag {
            type empty;
          }
          leaf port-id {
            type string;
          }
          leaf ingress {
            type empty;
          }
          leaf egress {
            type empty;
          }
        }
        list sap {
          // NCS patched for predictable order
          ordered-by user;
          key "sap-id";
          leaf sap-id {
            type string;
          }
          leaf ingress {
            type empty;
          }
          leaf egress {
            type empty;
          }
        }
        list subscriber {
          // NCS patched for predictable order
          ordered-by user;
          key "sub-ident-string";
          leaf sub-ident-string {
            type string;
          }
          leaf sap {
            type string;
          }
          leaf ip {
            type string;
          }
          leaf mac {
            type ncs_template_ieee-mac;
          }
          leaf sla-profile-name {
            type string;
          }
          leaf fc {
            type string;
          }
          leaf ingress {
            type empty;
          }
          leaf egress {
            type empty;
          }
        }
        leaf shutdown {
          // NCS drop default statement
          type string;
        }
      }
    }
    container commands;
  }
}
