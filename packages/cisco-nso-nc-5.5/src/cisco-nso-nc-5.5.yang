module cisco-nso-nc-5.5 {
  yang-version 1.1;
  namespace "http://tail-f.com/ns/ned-id/cisco-nso-nc-5.5";
  prefix cisco-nso-nc-5.5;

  import cisco-nso-nc {
    prefix family;
  }

  identity cisco-nso-nc-5.5 {
    base family:cisco-nso-nc;
  }
}
