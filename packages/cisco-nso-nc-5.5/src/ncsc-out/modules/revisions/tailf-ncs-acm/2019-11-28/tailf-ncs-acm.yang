module tailf-ncs-acm {
  // Generated by yanger -t ncs
  tailf:mount-id "cisco-nso-nc-5.5:cisco-nso-nc-5.5";
  tailf:ncs-device-type "netconf";

  namespace "http://tail-f.com/yang/ncs-acm";
  prefix tnacm;

  import ietf-netconf-acm {
    prefix nacm;
  }
  import tailf-common {
    prefix tailf;
  }
  import tailf-ncs-internal-mount {
    prefix ncs;
  }

  organization
    "Tail-f Systems";
  description
    "This module augments ietf-netconf-acm with additional
     access control data specific to NCS.

     Copyright 2019 Cisco Systems, Inc.
     All rights reserved.
     Permission is hereby granted to redistribute this file without
     modification.";

  revision 2019-11-28 {
    description
      "Initial revision.

       Released as part of NCS-5.3.";
  }

  augment "/ncs:devices/ncs:template/ncs:ned-id/ncs:config/nacm:nacm" {
    leaf enforce-nacm-on-services {
      type string;
      // NCS drop default statement
      description
        "By design NACM rules are ignored for changes done by services -
         FASTMAP, Reactive FASTMAP, or Nano services.

         This leaf allows NCS administrators to control this behavior:
         NCS administrators can enforce NACM rules even on changes done by
         services.";
    }
  }
  augment "/ncs:devices/ncs:device/ncs:live-status/nacm:nacm" {
    leaf enforce-nacm-on-services {
      tailf:ncs-device-type "netconf";
      tailf:display-when "not(../../../ncs:module) or ../../../ncs:module[ncs:name='tailf-ncs-acm'] or (../../../ncs:live-status-protocol[not(ncs:capability)]) or (../../../ncs:live-status-protocol/ncs:capability/ncs:module[.='tailf-ncs-acm'])";
      type boolean;
      // NCS drop default statement
      description
        "By design NACM rules are ignored for changes done by services -
         FASTMAP, Reactive FASTMAP, or Nano services.

         This leaf allows NCS administrators to control this behavior:
         NCS administrators can enforce NACM rules even on changes done by
         services.";
    }
  }
  augment "/ncs:devices/ncs:device/ncs:config/nacm:nacm" {
    leaf enforce-nacm-on-services {
      tailf:ncs-device-type "netconf";
      tailf:display-when "not(../../../ncs:module) or ../../../ncs:module[ncs:name='tailf-ncs-acm']";
      type boolean;
      default "false";
      description
        "By design NACM rules are ignored for changes done by services -
         FASTMAP, Reactive FASTMAP, or Nano services.

         This leaf allows NCS administrators to control this behavior:
         NCS administrators can enforce NACM rules even on changes done by
         services.";
    }
  }
}
